/*
 * Copyright (c) 2020 PANTHEON.tech, s.r.o. and others.  All rights reserved.
 *
 * This program and the accompanying materials are made available under the
 * terms of the Eclipse Public License v1.0 which accompanies this distribution,
 * and is available at http://www.eclipse.org/legal/epl-v10.html
 */
module test-listener {
    yang-version 1;
    namespace "urn:opendaylight:test-listener";
    prefix "t";

    revision "2020-10-22" {
    }

    notification deprecated-notification {
        description "Just a testing deprecated notification.";
        status deprecated;
    }

    notification obsolete-notification {
        description "Just a testing obsolete notification.";
        status obsolete;
    }

    notification test-notification {
        description "Just a testing notification.";
    }
}
