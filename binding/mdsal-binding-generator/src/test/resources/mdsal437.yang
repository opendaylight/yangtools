module mdsal437 {
    prefix mdsal437;
    namespace mdsal437;

    grouping grp {
        anyxml grp;
    }

    container cont {
        anyxml cont;

        uses grp;
    }

    list lst {
        uses grp;
    }

    anyxml any;
}
