module grouping_uses_notification {

    namespace "urn:grouping:uses:notification";
    prefix "sbd";

    organization "OPEN DAYLIGHT";
    contact "http://www.opendaylight.org/";

    revision 2013-07-18 {
    }

    grouping grouping-notification-test {
        container container-grouping-notification-test {
            leaf leaf-container-grouping-notification-test {
                type uint32;
            }
        }
        leaf-list leaffllist-grouping-notification-test {
            type string;
        }
    }

//grouping in NOTIFICATION
    notification notification-test {
        leaf leaf-notification-test {
            type string;
        }
        uses grouping-notification-test;
    }
}
