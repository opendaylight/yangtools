module module-refine {

    namespace "urn:refine:module";
    prefix "sbd";

    organization "OPEN DAYLIGHT";
    contact "http://www.opendaylight.org/";

    revision 2013-9-11 {
    }

    grouping grp {
        leaf-list lflst {
            type string;
            min-elements 16;
            max-elements 32;
            must "old = 44";
        }
        choice chc {
            default second;
            case first {
                leaf lf-of-case1 {
                    type int32;
                }
            }
            case second {
                leaf lf-of-case2 {
                    type int16;
                }
            }
        }
        choice chc2 {
            mandatory "true";
            case first2 {
            }
            case second2 {
            }
        }
        anyxml data {
            mandatory "true";
            must "something = 7";
        }
    }

    uses grp {
        refine lflst {
            min-elements 32;
            max-elements 64;
            must "new = 57";
            new-subnode "some value from lflst";
        }
        refine chc {
            default first;
            new-subnode-chc "some value from chc";
        }
        refine chc2 {
            mandatory "false";
        }
        refine data {
            mandatory "false";
            must "something-else = 9";
            new-subnode-data "some value from data";
        }
    }
}
