module leafref-valid {
    namespace "urn:xml:ns:yang:lrv";
    prefix lrv;
    revision "2015-02-25";

    list neighbor {
        description "List of neighbors.";
        leaf neighbor-id {
            type leafref {
                path "../../neighbor/mystring";
            }
            description "Neighbor.";
        }

        leaf neighbor2-id {
            type leafref {
                path "/lrv:neighbor/lrv:mystring";
            }
        }

        leaf mystring {
            type string;
        }
    }
}
