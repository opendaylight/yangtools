module simple-string-demo {

    namespace "urn:simple:string:demo";
    prefix "sbd";

    organization "OPEN DAYLIGHT";
    contact "http://www.opendaylight.org/";

    revision 2013-06-18 {

    }


    typedef typedef-string {
        type string {
            length "40";
            pattern "[0-9A-F]*";
            pattern "[B-D]*";
            pattern "[4-7]*";
        }
    }

}
