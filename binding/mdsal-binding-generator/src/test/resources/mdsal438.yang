module mdsal438 {
    yang-version 1.1;
    prefix mdsal438;
    namespace mdsal438;

    grouping grp {
        anydata grp;
    }

    container cont {
        anydata cont;

        uses grp;
    }

    list lst {
        uses grp;
    }

    anydata any;
}
