module bug8449 {
    yang-version 1;
    namespace "bug8449";
    prefix "tst";

    revision "2017-05-16" {
    }

    typedef name1-ref {
        type leafref {
            path "/tst:top/tst:name1";
        }
    }

    typedef name2-ref {
        type leafref {
            path "/tst:top/tst:name2";
        }
    }

    typedef name3-ref {
        type string;
    }

    container top {
        leaf name1 {
            type string;
        }
        leaf name2 {
            type string;
        }
    }

    container test {
        leaf ref {
            type name3-ref;
        }
    }

    container cont {
        leaf ref {
            type union {
                type name1-ref;
                type name2-ref;
            }
            mandatory true;
        }
    }
}
