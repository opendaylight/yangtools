module leafref-relative-circular {
    namespace "urn:xml:ns:yang:lrc";
    prefix lrc;
    revision "2023-06-22";

    list neighbor {
        description
          "List of neighbors.";
        leaf neighbor-id {
            type leafref {
                path "../../neighbor/neighbor2-id";
            }
            description "Neighbor.";
        }

        leaf neighbor2-id {
            type leafref {
                 path "../../neighbor/neighbor3-id";
            }
            description "Neighbor.";
        }

        leaf neighbor3-id {
            type leafref {
                path "../../neighbor/neighbor-id";
            }
           description "Neighbor.";
        }
    }
}
