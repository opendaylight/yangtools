module baz {
  yang-version 1.1;
  namespace "baz";
  prefix baz;

  import foo {
    prefix foo;
  }

  container baz-cont {
    uses foo:foo-grp {
      augment foo-act/input {
        leaf baz-aug-leaf {
          type string;
        }
      }
    }
  }
}
