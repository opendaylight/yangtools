module opendaylight-knock-knock-rpc {
    namespace "urn:opendaylight:params:xml:ns:yang:md:sal:knock-knock";
    prefix knock-knock;

    revision 2018-07-23;

    rpc knock-knock {
        input {
            leaf knocker-id {
                type instance-identifier;
            }

            leaf question {
                type string;
            }
        }

        output {
            leaf answer {
                type string;
            }
        }
    }
}
