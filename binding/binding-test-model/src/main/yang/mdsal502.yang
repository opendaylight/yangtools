module mdsal502 {
  namespace mdsal502;
  prefix mdsal502;

  grouping MyGrp {
    leaf MyGrp {
      type string;
    }
  }

  grouping My_grp {
    leaf My_grp {
      type string;
    }
  }

  grouping my-grp {
    leaf my-grp {
      type string;
    }
  }

  grouping my.grp {
    leaf my.grp {
      type string;
    }
  }

  container my-grp {
    uses MyGrp;
  }

  container foo {
    leaf bar {
      type string;
    }
    leaf Bar {
      type int32;
    }
  }

  container Foo {
    leaf bar {
      type int16;
    }
    leaf Bar {
      type binary;
    }
  }

  typedef SomeType {
    type string;
  }

  typedef someType {
    type int32;
  }
}
