module opendaylight-test-notification {
    yang-version 1.1;
    namespace "urn:opendaylight:params:xml:ns:yang:controller:md:sal:test:bi:ba:notification";
    prefix "ntf";

    description
        "Test model for testing of registering notification listener and publishing of notification.";

    revision "2015-02-05" {
        description
            "Initial revision";
    }

    notification out-of-pixie-dust-notification {
        description "Just a testing notification that we can not fly for now.";

        leaf reason {
            type string;
        }

        leaf days-till-new-dust {
            type uint16;
        }
    }

    container wood {
        typedef tree-id {
            type uint64;
        }

        grouping tree-fell-properties {
            // There might have been a mime around, do you care?
            leaf hit-mime {
                type boolean;
            }
        }

        notification a-tree-fell {
            leaf tree-id {
                type tree-id;
            }
            uses tree-fell-properties;
        }

        grouping notif-grp {
            notification in-grp;
        }

        uses notif-grp;

        list tree {
            leaf id {
                type tree-id;
            }
            key id;

            notification i-fell {
                uses tree-fell-properties;
            }

            uses notif-grp;
        }
    }

    augment /wood/tree/in-grp {
        leaf from-augment {
            type string;
        }
    }
}
