/*
 * Copyright (c) 2013 Cisco Systems, Inc. and others.  All rights reserved.
 *
 * This program and the accompanying materials are made available under the
 * terms of the Eclipse Public License v1.0 which accompanies this distribution,
 * and is available at http://www.eclipse.org/legal/epl-v10.html
 */
module list-composite-key {
    yang-version 1;
    namespace "urn:composite.key";
    prefix "scd";

    organization "OPEN DAYLIGHT";
    contact "http://www.opendaylight.org/";

    description "
        This module contains the definitions of elements that creates network
        topology i.e. definition of network nodes and links. This module is
        not designed to be used solely for network representation. This module
        SHOULD be used as base module in defining the network topology.
    ";

    revision "2013-02-27" {
        reference " WILL BE DEFINED LATER";
    }

    container list-parent-container {

        list composite-key-list {
            key "key1 key2";

            leaf key1 {
                type int8;
            }

            leaf key2 {
                type string;
            }

            list inner-list {
                key "key1";

                leaf key1 {
                    type uint16;
                }

                leaf foo {
                    type int32;
                }
            }

            leaf foo {
                type int32;
            }
        }

        list no-key-list {
            leaf foo {
                type int32;
            }

            leaf bar {
                type decimal64 {
                    fraction-digits 2;
                }
            }
        }
    }
}
