module mdsal-395 {
    yang-version 1.1;
    namespace "mdsal-395";
    prefix "mdsal395";

    grouping grp {
        leaf implemented-interface {
            type string;
        }
    }

    grouping notif-grp {
        notification grp-notif {
            leaf foo {
                type string;
            }
        }
    }

    container cont {
        leaf implemented-interface {
            type string;
        }

        uses notif-grp;
    }

    notification notif {
        leaf implemented-interface {
            type string;
        }
    }

}
