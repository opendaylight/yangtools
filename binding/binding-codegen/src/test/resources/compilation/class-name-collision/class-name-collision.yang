/*
 * Copyright (c) 2013 Cisco Systems, Inc. and others.  All rights reserved.
 *
 * This program and the accompanying materials are made available under the
 * terms of the Eclipse Public License v1.0 which accompanies this distribution,
 * and is available at http://www.eclipse.org/legal/epl-v10.html
 */
module class-name-collision {
    yang-version 1;
    namespace "urn:class:name:collision";
    prefix "bar";

    revision "2014-04-28" {

    }

    list string {
    }

    list string-builder {
    }

    list class {
    }

    list set {
    }

    list map {
    }
}
