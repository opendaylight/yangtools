/*
 * Copyright (c) 2022 PANTHEON.tech s.r.o. All rights reserved.
 *
 * This program and the accompanying materials are made available under the
 * terms of the Eclipse Public License v1.0 which accompanies this distribution,
 * and is available at http://www.eclipse.org/legal/epl-v10.html
 */
module presence-container {
    yang-version 1.1;
    namespace "urn:opendaylight:presence-container";
    prefix pc;

    revision 2022-03-17 {
        description
        "Initial revision.";
    }

    container directory {
        list user {
            key userId;
            leaf userId {
                type string;
            }
        }

        container data {
            leaf value {
                type string;
            }
        }

        container scp {
            presence "If present SCP is enabled.";
        }
    }
}
