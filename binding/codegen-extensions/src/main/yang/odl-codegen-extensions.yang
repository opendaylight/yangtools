module odl-codegen-extensions {
    yang-version 1;
    namespace "urn:opendaylight:yang:extension:codegen";
    prefix "oce";

    description
        "YANG extensions for code generation.

         Copyright (c) 2024 PANTHEON.tech, s.r.o. and others.  All rights reserved.

         This program and the accompanying materials are made available under the
         terms of the Eclipse Public License v1.0 which accompanies this distribution,
         and is available at http://www.eclipse.org/legal/epl-v10.html";

    revision "2024-06-27" {
        description "Initial revision";
    }

    extension "augment-identifier" {
        description
           "YANG language extension which assigns an identifier to augmentation. Augment identifier
            is used to identify a specific augment statement by a name.

            The identifier syntax is defined formally defined by the rule 'identifier' in
            Section 12 of RFC 6020.

            All augment identifiers defined in a namespace MUST be unique. The namespace of augment
            identifiers is shared by module and its submodules.";

            /*
                Discussion:
                This extension allows for ease of development / debug of YANG modules and it is
                suitable for code generation, where each augment statement is nicely identified by
                unique name instead of combination of augment target and when condition.
            */
        argument "identifier";
    }
}
