module leafref-relative-invalid {
    namespace "urn:xml:ns:yang:lrr";
    prefix lrr;
    revision "2015-02-25";

    list neighbor {
         description
           "List of neighbors.";
         leaf neighbor-id {
             type leafref {
                 path "../../neighbor/neighbor-id";
             }
             description "Neighbor.";
         }
    }
}
