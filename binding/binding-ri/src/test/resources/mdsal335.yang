module mdsal335 {
    namespace "mdsal335";
    prefix "mdsal335";

    typedef ipv4-address {
        type string {
            pattern
                '(([0-9]|[1-9][0-9]|1[0-9][0-9]|2[0-4][0-9]|25[0-5])\.){3}'
                +  '([0-9]|[1-9][0-9]|1[0-9][0-9]|2[0-4][0-9]|25[0-5])'
                + '(%[\p{N}\p{L}]+)?';
        }
    }

    typedef ipv4-address-no-zone {
        type mdsal335:ipv4-address {
            pattern '[0-9\.]*';
        }
    }
}
