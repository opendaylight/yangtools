module listener-conflict {
  namespace listener-conflict;
  prefix lc;

  container listener-conflict-listener; // results in ListenerConflictListener
  notification bar; // Triggers ListenerConflictListener generation for module
}
