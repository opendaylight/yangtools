module foo {
    yang-version 1;
    namespace "urn:yang.foo";
    prefix "foo";

    revision "2016-01-01" {
    }

    container boolean-container {
        list boolean-list {
            key "boolean-leaf-1 boolean-leaf-2";
            leaf boolean-leaf-1 {
                type boolean;
            }
            leaf boolean-leaf-2 {
                type boolean;
            }
        }

        list boolean-list-int {
            key "boolean-leaf-int";
            leaf boolean-leaf-int {
                type int8;
            }
        }
    }
}
