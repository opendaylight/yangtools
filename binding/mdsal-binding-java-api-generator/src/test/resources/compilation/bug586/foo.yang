/*
 * Copyright (c) 2013 Cisco Systems, Inc. and others.  All rights reserved.
 *
 * This program and the accompanying materials are made available under the
 * terms of the Eclipse Public License v1.0 which accompanies this distribution,
 * and is available at http://www.eclipse.org/legal/epl-v10.html
 */
module foo {
    yang-version 1;
    namespace "urn:yang.foo";
    prefix "foo";

    revision "2014-03-28" {
    }


    container services {
        status deprecated;
        list service {
            status obsolete;
            key "permission";

            leaf permission {
                type enumeration {
                    enum permit;
                    enum deny;
                }
            }
        }
    }

}
