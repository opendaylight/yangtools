/*
 * Copyright (c) 2013 Cisco Systems, Inc. and others.  All rights reserved.
 *
 * This program and the accompanying materials are made available under the
 * terms of the Eclipse Public License v1.0 which accompanies this distribution,
 * and is available at http://www.eclipse.org/legal/epl-v10.html
 */
module test {
    yang-version 1;
    namespace "urn:opendaylight:retest";
    prefix "t";

    revision "2013-10-08" {
    }

    grouping key-args {
        leaf name {
            type string;
        }
        leaf size {
            type int32;
        }
    }

    list links {
        uses key-args;
        key "size name id";

        leaf id {
            type int8;
        }

        anyxml text;
        choice level;
        container node;
        grouping link-group {
            leaf source {
                type int8;
            }
        }
        leaf links-id {
            type int32;
        }
        list node-list {
        }
        typedef nodes-type {
            type string;
        }
    }

}
