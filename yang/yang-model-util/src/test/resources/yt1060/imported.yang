module imported {
  namespace "imported";
  prefix imp;

  typedef foo {
    type string {
      pattern 'S(\d+G)?(\d+M)?';
    }
  }

  container root {
    leaf leaf1 {
      type string;
    }
  }
}
