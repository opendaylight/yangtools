submodule child {
  belongs-to parent {
    prefix par;
  }

  import imported {
    prefix imp;
  }

  container cont {
    leaf leaf1 {
      type leafref {
        path "/imp:root/imp:leaf1";
      }
    }
    leaf leaf2 {
        type imp:foo;
    }
  }
}
