module simple-container-yang {
  namespace "simple:container:yang";  

  prefix "smpdtp";
  revision 2013-11-12 {    
  }
  
  container cont {
  	container cont1 {
  	}
  	list lst1 {
  	}
  	list lst2 {
  	     leaf lf21 {
  	         type string;
  	     }
  	     leaf lf22 {
  	         type string;
  	     }
  	}
  	leaf-list lflst1 {
  		type string;
  	}
  	leaf lf1 {
  		type string;
  	}
  }
}
