module simple-module {

    namespace "simple.yang";
    prefix sim;

    container root-container {
        container sub-container {
            container sub-sub-container {
            }
        }
    }
    
//    container sim:root-container2 {
//        container sub-container2 {
//            container "sim:sub-sub-container2" {
//            }
//        }
//    }
    
    container root-container2 {
        uses grp;
    }
    
    grouping grp {
        container sub-container2 {
            container "sub-sub-container2" {
            }
        }
    }
}
