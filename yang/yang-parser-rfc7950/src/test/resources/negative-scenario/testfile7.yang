module testfile7 {
    yang-version 1;
    namespace "urn:simple.test7.demo";
    prefix "t7";

    import testfile8 {
        prefix "t8";
        revision-date 2013-08-03;
    }

    organization "opendaylight";
    contact "http://www.opendaylight.org/";

    revision "2013-08-03" {
        reference " WILL BE DEFINED LATER";
    }

    augment "/t8:interfaces/t8:ifEntry" {
        when "t8:leafType='ds1'";
        leaf linkleaf {
            mandatory true;
            type binary;
        }
    }

}
