module importedtest {
    yang-version 1;
    namespace "urn:imptst:yang";
    prefix "imptst";

    description "This is a to be imported test module";

    revision 2015-03-20;

    container myimportedcontainer {
        leaf myimportedleaf {
            type string;
        }
    }
}
