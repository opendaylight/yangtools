module importedrevtest {
    yang-version 1;
    namespace "urn:imprevtst:yang";
    prefix "imprevtst";

    description "This is a test module";

    revision 2015-06-02;

    typedef date-and-time {
        type string {
            pattern "[0-9]+";
        }
    }
}
