module foo {
    namespace foo;
    prefix foo;
    yang-version 1.1;

    import bar {
        prefix bar;
        revision-date 2017-01-20;
    }

    revision 2017-01-20;

    deviation "/bar:my-leaf" {
        deviate delete {
            units seconds;
            default 100;
            bar:custom-property-without-arg;
        }
    }

    deviation "/bar:my-leaf-list" {
        deviate delete {
            default "def-val-1";
            default "def-val-2";
            must "a = 1 or b = 2";
            must "x != y";
        }
    }

    deviation "/bar:my-list" {
        deviate delete {
            unique "my-leaf-a my-leaf-b";
            unique "my-leaf-c my-leaf-d";
            bar:custom-property "arg";
            bar:custom-property "another arg";
        }
    }

    deviation "/bar:my-cont/bar:my-aug-leaf" {
        deviate delete {
            default "def-val";
            units "minutes";
            must "x = 1";
            bar:custom-property-without-arg;
        }
    }

    deviation "/bar:my-cont/bar:my-used-leaf" {
        deviate delete {
            default "def-val-added-by-refine";
            bar:custom-property-without-arg;
            units "days";
            must "y = 5";
        }
    }
}
