module bar {
    namespace bar;
    prefix bar;

    revision 2017-02-01;

    container my-cont {
        uses my-grouping {
            refine my-used-leaf {
                default "def-val-added-by-refine";
            }
        }
    }

    grouping my-grouping {
        leaf my-used-leaf {
            type int32;
        }
    }
}
