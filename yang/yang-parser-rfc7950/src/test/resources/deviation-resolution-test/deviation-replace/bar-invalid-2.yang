module bar {
    namespace bar;
    prefix bar;
    yang-version 1.1;

    revision 2017-01-20;

    leaf-list my-leaf-list {
        type string;
        default "default value one";
        default "default value two";
    }
}
