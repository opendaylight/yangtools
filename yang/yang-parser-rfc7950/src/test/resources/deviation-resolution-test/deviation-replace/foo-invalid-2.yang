module foo {
    namespace foo;
    prefix foo;
    yang-version 1.1;

    import bar {
        prefix bar;
        revision-date 2017-01-20;
    }

    revision 2017-01-20;

    deviation "/bar:my-leaf-list" {
        deviate replace {
            default "new default value";
        }
    }
}
