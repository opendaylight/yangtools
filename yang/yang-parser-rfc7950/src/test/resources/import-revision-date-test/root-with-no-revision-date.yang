module root-with-no-revision-date {
    namespace "urn:opendaylight.org/root-with-no-revision-date";
    prefix "root-no-date";

    import imported-module-with-no-revision-date {
        prefix "imported-no-date";
    }
}
