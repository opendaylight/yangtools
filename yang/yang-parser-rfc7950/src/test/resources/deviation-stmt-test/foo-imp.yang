module foo-imp {
    namespace "fimp-ns";
    prefix "fimp";

    revision 2016-06-23;

    container test-container {
        leaf test-leaf {
            type string;
        }

        leaf test-leaf-2 {
            type string;
        }

        leaf-list test-leaf-list {
            type int32;
            min-elements 3;
            must "daytime or time";
            must "time or daytime";
            units minutes;
        }

        list test-list {
            key key-leaf;
            unique "list-leaf-1 list-leaf-2";
            unique "list-leaf-3 list-leaf-4";

            leaf key-leaf {
                type string;
            }

            leaf list-leaf-1 {
                type string;
            }

            leaf list-leaf-2 {
                type string;
            }

            leaf list-leaf-3 {
                type string;
            }

            leaf list-leaf-4 {
                type string;
            }
        }
    }
}
