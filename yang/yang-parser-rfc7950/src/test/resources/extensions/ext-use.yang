module ext-use {
    ext:id "http://opendaylight.org";
    yang-version 1;
    ext:id "http://opendaylight.org";

    ext:id2 "73354";
    ext:name "test-name";

    namespace "urn:simple.extension.use";
    ext:id "http://opendaylight.org";

    ext:name "test-name";

    prefix "ext-use";
    ext:id "http://opendaylight.org";
    ext:name "test-name";

    import ext-typedef { prefix "ext"; }

    organization "opendaylight";
    contact "http://www.opendaylight.org/";

    description "Model for testing of used extensions across model.";

    revision "2014-08-07" {
        reference "Initial revision.";
    }

    leaf value {
      ext:simple-ext-w-arg "key:value";
      type uint32;
      description "value";
    }

    grouping inner-ext {
        ext:simple-ext-w-arg "value:test";

        leaf inner-value {
          ext:simple-ext-w-arg "key:inner-value";
          type uint32;
          description "value";
        }
    }

    container cont-ext {
        ext:simple-ext-w-arg "value:test";

        leaf inner-value {
            ext:simple-ext-w-arg "value:test";
            type string;
        }
    }
}
