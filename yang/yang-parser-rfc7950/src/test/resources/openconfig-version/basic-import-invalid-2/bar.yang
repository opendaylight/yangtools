module bar {
    namespace "bar";
    prefix bar;
    yang-version 1;

    import openconfig-extensions { prefix oc-ext; revision-date 2017-01-29; oc-ext:openconfig-version "0.0.1"; }

    revision "2016-01-31" {
        description "Initial version";
    }
    oc-ext:openconfig-version "1.1.2";

    container root {
    }
}
