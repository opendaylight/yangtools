module bar {
    namespace "bar";
    prefix bar;
    yang-version 1.1;

    import openconfig-extensions { prefix oc-ext; oc-ext:openconfig-version "1.2.210"; }
    import foobar { prefix foobar; oc-ext:openconfig-version "2.25.3"; }

    revision "2016-01-04" {
        description "Not-imported version";
    }
    oc-ext:openconfig-version "2.200.200";

    container root {
        container test-container {
            uses foobar:test-grouping;
        }
    }

    leaf-list should-not-be-present {
        type uint32;
        description "List of integers";
    }
}
