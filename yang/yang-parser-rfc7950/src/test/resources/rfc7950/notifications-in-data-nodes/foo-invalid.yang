module foo {
    namespace foo;
    prefix foo;
    yang-version 1.1;

    rpc my-rpc {
        input {
            container i {
            }
        }
        output {
            container o {
            }
        }
    }

    grouping grp {
        notification grp-notification {
        }
    }

    augment "/my-rpc/input/i" {
        uses grp;
    }
}
