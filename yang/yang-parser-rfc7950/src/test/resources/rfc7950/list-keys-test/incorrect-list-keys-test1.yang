module incorrect-list-keys-test1 {
    yang-version 1.1;
    namespace "incorrect-list-keys-test1";
    prefix "test";

    revision 2017-02-06 {
        description "Bug 6855: Test disallowing IF-FEATURE on list key";
    }

    list invalid-list-b {
        key "b";
        leaf b {
            if-feature feature-b;
            type string;
        }
    }
}
