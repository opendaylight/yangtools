module foo {
    namespace foo-namespace;
    prefix foo-prefix;
    yang-version 1.1;

    revision 2016-12-13;

    container root {
    }

    container top {
        action top-action {
        }
    }

    list top-list {
        key key-leaf;

        leaf key-leaf {
            type string;
        }

        action top-list-action {
        }
    }

    grouping grp {
        action grp-action {
        }
    }

    augment "/root" {
        uses grp;
        action aug-action {
        }
    }
}
