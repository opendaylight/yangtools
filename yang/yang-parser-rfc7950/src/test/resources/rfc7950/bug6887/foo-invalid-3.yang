module foo {
    namespace foo;
    prefix foo;
    yang-version 1.1;

    revision 2017-02-02;

    typedef my-base-enumeration-type {
        type enumeration {
            enum white {
                value 1;
            }
            enum yellow {
                value 2;
            }
            enum red {
                value 3;
            }
            enum black {
                value 4;
            }
        }
    }

    typedef my-derived-enumeration-type {
        type my-base-enumeration-type {
            enum yellow {
                value 2;
            }
            enum red {
                value 3;
            }
            enum black {
                value 4;
            }
        }
    }

    leaf my-enumeration-leaf {
        type my-derived-enumeration-type {
            enum yellow;
            enum red {
                value 5;
            }
        }
    }
}
