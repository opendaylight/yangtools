module bar {
    namespace bar-ns;
    prefix bar-prefix;

    include subbar {
        revision-date 2017-03-14;
    }

    revision 2017-03-14;

    container my-cont {
        leaf my-leaf {
            type string;
        }
    }
}
