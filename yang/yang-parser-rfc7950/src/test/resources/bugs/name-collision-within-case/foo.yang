module foo {
    yang-version 1.1;
    namespace foo;
    prefix foo;

    revision "2018-02-11";

    grouping foo {
      container bar {

      }
    }

    container cont {
      choice bar {
        case foo {
          uses foo;
        }
      }
    }

    augment "/cont/bar" {
      case foo2 {
        uses foo;
      }
    }
}
