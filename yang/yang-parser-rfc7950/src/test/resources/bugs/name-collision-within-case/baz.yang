module baz {
    yang-version 1.1;
    namespace baz;
    prefix baz;

    revision "2018-02-28";

    grouping foo {
      container bar {

      }
    }

    container cont {
      choice bar {
        case foo {
          uses foo;
        }
      }

      container bar {

      }
    }
}
