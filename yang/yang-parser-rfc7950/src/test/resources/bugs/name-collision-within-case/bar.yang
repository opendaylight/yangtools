module bar {
    yang-version 1.1;
    namespace bar;
    prefix bar;

    revision "2018-02-11";

    grouping foo {
      container bar {

      }
    }

    container cont {
      choice bar {
        case foo {
          uses foo;
        }
      }
    }

    augment "/cont" {
      choice foo {
        case foo {
          uses foo;
        }
      }
    }
}
