module foo {
  yang-version 1.1;
  namespace foo;
  prefix foo;

  import xyzzy { prefix xyzzy; }

  feature foo;

  container foo {
    if-feature foo;
  }

  augment /xyzzy:xyzzy/xyzzy:named {
    container foo {
      if-feature foo;
    }
  }
}
