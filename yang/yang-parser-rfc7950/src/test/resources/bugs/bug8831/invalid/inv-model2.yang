module inv-model2 {
    yang-version 1.1;
    namespace "http://www.inv-model2.com";
    prefix ex;

    revision 2017-07-10;

    feature my-feature {
        description "my feature";
    }

    typedef enum-first {
        type union {
            type enumeration {
                enum "any" {
                    if-feature my-feature;
                }
            }
            type uint16;
        }
    }

    container top {
        leaf enum-first-leaf {
            type enum-first;
            default "any";
        }
    }
}
