module foo {
  namespace foo;
  prefix foo;

  grouping grp {
    leaf foo {
      // Two substatements to defeat singleton list elimination
      type string;
      description "desc";
    }
  }

  uses grp;
}
