module typedef {
    namespace typedef;
    prefix tdef;

    revision "2017-12-20";

    container top {
        container nested {
            typedef foo {
                type string;
            }
        }

        typedef foo {
            type string;
        }
    }
}
