module bar {
    namespace "bar";
    prefix bar;

    import foo { prefix foo; revision-date 2016-09-08; }

    revision 2016-09-08;

    augment /foo:root {
        container bar {
            container bar1 {
                leaf m {
                    mandatory true;
                    type empty;
                }
            }
        }
    }
}
