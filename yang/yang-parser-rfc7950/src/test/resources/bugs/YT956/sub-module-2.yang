submodule sub-module-2 {
    yang-version 1.1;

    belongs-to mainmodule {
        prefix mm;
    }

    import another-module {
        prefix am;
    }

    include sub-module-1;

    grouping dummygrouping {
        leaf dummyleaf {
            type string;
            mandatory true;
        }
    }

    augment '/am:another-container/mm:first-augment' {
        uses dummygrouping;
    }
}
