module another-module {
    yang-version 1.1;
    namespace "http://www.example.com/anothermodule";
    prefix am;

    container another-container {
        leaf type {
            type string;
            mandatory true;
        }
    }
}
