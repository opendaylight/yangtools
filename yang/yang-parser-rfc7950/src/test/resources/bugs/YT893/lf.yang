module lf {
    namespace "urn:lf";
    prefix lf;

    list foo {
        unique "a
                b";

        leaf a {
            type string;
        }
        leaf b {
            type string;
        }
    }
}
