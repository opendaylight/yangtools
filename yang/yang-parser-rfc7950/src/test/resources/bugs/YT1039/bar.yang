module bar {
  namespace bar;
  prefix bar;
  import foo { prefix foo; }

  rpc bar {
    input {
      uses foo:arg-path {
        refine path {
          mandatory false;
        }
      }
    }
  }
}
