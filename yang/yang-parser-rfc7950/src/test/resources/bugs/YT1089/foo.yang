module foo {
    namespace urn:foo;
    prefix foo;

    description +something;
    contact contact++;
    organization organiza++tion;

    leaf foo {
      type string;
      default +;
      description 'squot' + "dquot";
      reference "+" + '+';
    }

    leaf bar {
      type string;
      default ++;
      description "+ + ++";
      reference "++ + +";
    }
}
