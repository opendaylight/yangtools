module lib-1 {
    namespace lib-1;
    prefix lib-1;

    import lib-2 { prefix lib-2; revision-date 2000-01-01; }
    import missing-lib { prefix missing; revision-date 2000-01-01; }

    revision 2000-01-01;

    container root {
    }
}
