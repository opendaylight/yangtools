module string-test {
    namespace "test";
    prefix test;

    description "  Unascaping examples:" +
                " \\,\n,\t  \"string enclosed in double quotes\" end
                abc \\\\\\ \\t \\\nnn";
}
