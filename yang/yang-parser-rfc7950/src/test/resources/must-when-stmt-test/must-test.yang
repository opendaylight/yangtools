module must-test {
    namespace "urn:opendaylight.org/must-test";
    prefix "mt";

    container interface {
         presence "some text";

         leaf ifType {
             type enumeration {
                 enum ethernet;
                 enum atm;
             }
         }
         leaf ifMTU {
             type uint32;
         }
         must "ifType != 'ethernet' or " +
              "(ifType = 'ethernet' and ifMTU = 1500)" {
             error-app-tag "An ethernet error";
             error-message "An ethernet MTU must be 1500";
         }
         must "ifType != 'atm' or " +
              "(ifType = 'atm' and ifMTU <= 17966 and ifMTU >= 64)" {
             error-app-tag "An atm error";
             error-message "An atm MTU must be 64 .. 17966";
         }
    }
}
