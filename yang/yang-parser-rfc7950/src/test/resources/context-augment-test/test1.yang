module test1 {

    yang-version 1;
    namespace "urn:simple.demo.test1";
    prefix "t1";

    import test3 {
        prefix "t3";
        revision-date 2013-06-18;
    }

    import test2 {
        prefix "t2";
        revision-date 2013-06-18;
    }

    import test4 {
        prefix "t4";
        revision-date 2013-06-18;
    }

    organization "opendaylight";
    contact "WILL-BE-DEFINED-LATER";
        revision 2013-06-18 {
    }

    augment "/t4:interfaces/t4:ifEntry/t3:augment-holder/t2:schemas" {
        when "t4:ifType='ds0'";
        leaf id {
            type string;
        }
    }

}
