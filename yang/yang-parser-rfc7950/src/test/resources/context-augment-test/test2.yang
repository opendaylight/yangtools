module test2 {

    yang-version 1;
    namespace "urn:simple.demo.test2";
    prefix "t2";

    import test3 {
        prefix "t3";
        revision-date 2013-06-18;
    }

    import test4 {
        prefix "t4";
        revision-date 2013-06-18;
    }

    organization "opendaylight";
    contact "WILL-BE-DEFINED-LATER";
        revision 2013-06-18 {
    }

    augment "/t4:interfaces/t4:ifEntry/t3:augment-holder" {
        when "t4:ifType='ds0'";
        leaf ds0ChannelNumber {
            type string;
        }
        leaf interface-id {
            type leafref {
                path "/t4:interfaces/t4:ifEntry/t4:ifIndex";
            }
        }
        leaf-list higher-layer-if {
            type leafref {
                path "/t4:interfaces/t4:ifEntry/t4:ifMtu";
            }
        }
        container schemas {
        }
    }

}
