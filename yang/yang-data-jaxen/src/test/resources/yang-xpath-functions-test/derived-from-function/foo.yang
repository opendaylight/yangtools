module foo {
    namespace foo-ns;
    prefix foo-prefix;
    yang-version 1.1;

    revision 2017-04-03;

    identity id-a1;
    identity id-a2;
    identity id-a3;
    identity id-a4;

    identity id-b1 {
        base id-a1;
        base id-a2;
    }

    identity id-b2 {
        base id-a3;
        base id-a4;
    }

    identity id-c1 {
        base id-b1;
        base id-b2;
    }

    container my-container {}
}
