module bar {
    namespace bar-ns;
    prefix bar-prefix;
    yang-version 1.1;

    import foo {
        prefix foo-prefix;
        revision-date 2017-04-03;
    }

    revision 2017-04-03;

    identity id-b3;
    identity id-b4;

    identity id-c2 {
        base foo-prefix:id-b2;
        base id-b3;
        base id-b4;
    }

    container my-container {
        list my-list {
            key key-leaf;

            leaf key-leaf {
                type string;
            }

            leaf idref-leaf {
                type identityref {
                    base foo-prefix:id-a3;
                }
            }
        }
    }
}
