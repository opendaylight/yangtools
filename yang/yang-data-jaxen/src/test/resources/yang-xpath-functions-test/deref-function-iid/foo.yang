module foo {
    namespace foo-ns;
    prefix foo-prefix;
    yang-version 1.1;

    revision 2017-04-03;

    container my-container {
        list my-list {
            key "key-leaf-a key-leaf-b";

            leaf key-leaf-a {
                type string;
            }

            leaf key-leaf-b {
                type string;
            }

            leaf iid-leaf {
                type instance-identifier;
            }

            leaf referenced-leaf {
                type string;
            }
        }
    }
}
