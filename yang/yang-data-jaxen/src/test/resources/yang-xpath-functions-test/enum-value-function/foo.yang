module foo {
    namespace foo-ns;
    prefix foo-prefix;
    yang-version 1.1;

    revision 2017-04-03;

    container my-container {
        list alarm {
            key severity;

            leaf ordinary-leaf {
                type string;
            }

            leaf severity {
                type enumeration {
                    enum cleared {
                        value 1;
                    }
                    enum indeterminate {
                        value 2;
                    }
                    enum minor {
                        value 3;
                    }
                    enum warning {
                        value 4;
                    }
                    enum major {
                        value 5;
                    }
                    enum critical {
                        value 6;
                    }
                }
            }
        }
    }
}
