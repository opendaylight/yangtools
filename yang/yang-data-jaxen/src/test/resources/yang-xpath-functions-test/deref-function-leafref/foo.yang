module foo {
    namespace foo-ns;
    prefix foo-prefix;
    yang-version 1.1;

    revision 2017-04-03;

    container my-container {
        list my-list {
            key "key-leaf-a key-leaf-b";

            leaf key-leaf-a {
                type string;
            }

            leaf key-leaf-b {
                type string;
            }

            leaf referenced-leaf {
                type string;
            }

            leaf referenced-leaf-list {
                type string;
            }
        }

        container my-inner-container {
            leaf abs-leafref-leaf {
                type leafref {
                    path "/my-container/my-list[key-leaf-a=current()/../ordinary-leaf-a]" +
                        "[key-leaf-b=current()/../ordinary-leaf-b]/referenced-leaf";
                }
            }

            leaf rel-leafref-leaf {
                type leafref {
                    path "../../foo-prefix:my-list[foo-prefix:key-leaf-a=current()/../ordinary-leaf-a]" +
                        "[key-leaf-b=current()/../ordinary-leaf-b]/foo-prefix:referenced-leaf";
                }
            }

            leaf leaf-list-leafref-leaf {
                type leafref {
                    path "/my-container/my-list[key-leaf-a=current()/../ordinary-leaf-a]" +
                        "[key-leaf-b=current()/../ordinary-leaf-b]/referenced-leaf-list";
                }
            }

            leaf ordinary-leaf-a {
                type string;
            }

            leaf ordinary-leaf-b {
                type string;
            }
        }
    }
}
