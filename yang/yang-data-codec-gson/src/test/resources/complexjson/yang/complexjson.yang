module complexjson {
    namespace "ns:complex:json";
    prefix cj;

    revision "2014-08-11" {
    }

    typedef wrapped-instance-identifier {
        description "Wrapped instance Identifier";
        type instance-identifier;
    }

    identity ident;

    container cont1 {

        leaf empty {
            type empty;
        }

        anyxml lf12-any;
        anyxml lf13-any;
        anyxml lf14-any;

        leaf lf11 {
            type int32;
        }

        leaf-list lflst11 {
            type string;
        }

        list lst11 {
            key "key111 lf111";
            leaf key111 {
                type string;
            }
            leaf lf111 {
                type string;
            }
            leaf lf112 {
                type wrapped-instance-identifier;
            }
            leaf lf113 {
                type string;
            }
        }

        list lst12 {
            leaf lf121 {
                type string;
            }
            leaf lf122 {
                type string;
            }
        }


        choice choc11 {
            case c11A {
                leaf lf13 {
                    type string;
                }
            }
            leaf lf16 {
                type string;
            }
        }

        choice choc12 {
            case c12A {
            }
        }
    }

    container cont2 {
        presence "presence container";
    }

    augment "/cont1/choc12" {
        case c12B {
            leaf lf17 {
                type string;
            }
        }
    }

    augment "/cont1" {
        container cont11 {
            leaf lf111 {
                type string;
            }
        }
    }

    augment "/cont1" {
        leaf lf12_1 {
            type string;
        }
        leaf lf12_2 {
            type string;
        }
    }

    augment "/cont1" {
        leaf lf12_3 {
            type string;
        }
    }

    augment "/cont1/choc11" {
        case c11B {
            leaf lf14_1  {
                type string;
            }
        }
    }

    augment "/cont1/choc11" {
        case c11C {
            leaf lf14_2  {
                type string;
            }
        }
    }

    augment "/cont1/choc11/c11A" {
        leaf lf15_11  {
            type bits {
                bit one;
                bit two;
                bit three;
            }
        }
        leaf lf15_12  {
            type identityref {
                base ident;
            }
        }

    }

    augment "/cont1/choc11/c11A" {
        leaf lf15_21 {
            type string;
        }
    }

    augment "/cont1" {
        /*ext:augment-identifier top-choice-augment1;*/
        choice augment-choice1 {
            case case1 {
                container case1-container {
                    leaf case1-leaf {
                        type string;
                    }
                }
            }

            case case2 {
                container case2-container {
                    leaf case2-leaf {
                        type string;
                    }
                }
            }
        }
    }

    augment "/cont1/augment-choice1/case1" {
        /*ext:augment-identifier top-choice-augment2;*/
        choice augment-choice2 {
            case case11 {
                container case11-choice-case-container {
                    leaf case11-choice-case-leaf {
                        type string;
                    }
                }
            }
        }
    }

}
