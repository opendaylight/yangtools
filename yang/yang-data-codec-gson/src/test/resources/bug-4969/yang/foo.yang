module foo {
    namespace "foo";
    prefix foo;

    import bar { prefix bar; revision-date 2016-01-22; }

    revision "2016-01-22" {
        description "Initial version";
    }

    container root {
        leaf ref1 {
            type bar:ref1;
        }
        leaf ref2 {
            type bar:ref2;
        }
        leaf ref3 {
            type bar:ref3;
        }
        leaf ref4 {
            type leafref {
                path "/bar:root/bar:l1";
            }
        }
    }
}
