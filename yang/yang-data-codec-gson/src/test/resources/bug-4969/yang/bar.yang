module bar {
    namespace "bar";
    prefix bar;

    revision "2016-01-22" {
        description "Initial version";
    }

    typedef ref1 {
        type ref1-2;
    }

    typedef ref2 {
        type ref2-2;
    }

    typedef ref3 {
        type ref3-2;
    }

    typedef ref1-2 {
        type leafref {
            path "/bar:root/bar:l1";
        }
    }

    typedef ref2-2 {
        type leafref {
            path "/bar:root/bar:l2";
        }
    }

    typedef ref3-2 {
        type leafref {
            path "/bar:root/bar:l3";
        }
    }

    container root {
        leaf l1 {
            type bits {
                bit a;
                bit b;
                bit c;
                bit d;
            }
        }
        leaf l2 {
            type leafref {
                path "/root/l1";
            }
        }
        leaf l3 {
            type leafref {
                path "../l1";
            }
        }
    }
}
