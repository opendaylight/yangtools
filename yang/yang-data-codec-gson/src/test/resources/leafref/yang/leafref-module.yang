module leafref-module {
    namespace "leafref:module";

    prefix "lfrfmo";

    import augment-leafref-module { prefix augleafref; revision-date 2014-12-16; }
    revision 2013-11-18 {
    }

    container cont {
        leaf lf1 {
            type int32;
        }
        leaf lf2 {
            type leafref {
                path "/cont/lf1";
            }
        }
        leaf lf4 {
            type augleafref:leafreftype;
        }
    }
}
