module yt1027 {
  namespace "yt1027.test";
  prefix tst;

  leaf uint64 {
    type uint64;
  }
 
  leaf int64 {
    type int64;
  }
 
  leaf decimal {
    type decimal64 {
      fraction-digits 1;
    }
  }
}
