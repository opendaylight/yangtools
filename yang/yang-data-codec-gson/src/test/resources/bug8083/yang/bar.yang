module example-barmod {

    namespace "http://example.com/barmod";
    prefix "barmod";

    import example-foomod {
        prefix "foomod";
    }

    augment "/foomod:top/foomod:foo-list" {
        container bar-container {
            leaf bar-leaf {
                type string;
            }
        }
    }
}
