module dataschemacontext {
    namespace "dataschemacontext";
    prefix dsc;

    container foo {
        choice bar {
            leaf baz {
                type string;
            }
        }
    }
}
