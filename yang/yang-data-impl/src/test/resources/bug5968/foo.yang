module foo {
    yang-version 1;
    namespace "foo";
    prefix foo;

    revision 2016-07-28 {
        description "test";
    }

    container root {
        list my-list {
            key "list-id";
            leaf list-id {
                type string;
            }
            leaf mandatory-leaf {
                type string;
                mandatory true;
            }
            leaf common-leaf {
                type string;
            }
        }
    }
}
