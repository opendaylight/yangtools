module foo-non-presence {
    yang-version 1;
    namespace "foo";
    prefix foo;

    revision 2016-05-17 {
        description "test";
    }

    container task-container {
        list task {
            key "task-id";

            leaf task-id {
                type string;
            }

            leaf task-mandatory-leaf {
                type string;
                mandatory true;
            }

            container task-data {
                leaf mandatory-data {
                    type string;
                    mandatory true;
                }
                leaf other-data {
                    type string;
                }
            }
        }
    }
}
