module order {
    namespace "order";
    prefix "order";
    revision "2016-02-17";
  container root {
    leaf id {
      type string;
    }
    container cont {
      leaf content {
        type string;
      }
    }

  }
}
