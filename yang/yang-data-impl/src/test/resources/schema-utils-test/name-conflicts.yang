module name-conflicts {
    namespace "my-namespace";
    prefix nc;

    grouping my-name {
        grouping my-name-nested {
            grouping my-name-nested2 {
            }
            container my-name-nested2 {
            }
        }
        container my-name-nested {
            grouping my-name-nested2 {
            }
            container my-name-nested2 {
            }
        }
    }

    container my-name {
        grouping my-name-nested {
            grouping my-name-nested2 {
            }
            container my-name-nested2 {
            }
        }
        container my-name-nested {
            grouping my-name-nested2 {
            }
            container my-name-nested2 {
            }
        }
    }

    grouping my-name-2 {
        grouping my-name-nested {
            grouping my-name-nested2 {
            }
            container my-name-nested2 {
            }
        }
        container my-name-2 {
            grouping my-name-nested2 {
            }
            container my-name-nested2 {
            }
        }
    }

    container my-name-2 {
        grouping my-name-nested {
            grouping my-name-nested2 {
            }
            container target {
            }
        }
        container my-name-nested {
            grouping my-name-nested2 {
            }
            container my-name-nested2 {
            }
        }
    }

    rpc my-name-3 {
        input {
            container con-1 {
                leaf l {
                    type string;
                }
            }
        }
        output {
            container con-2 {
                leaf l {
                    type string;
                }
            }
        }
    }

    grouping my-name-3 {
        container input {
            container con-3 {
                container l {
                }
            }
        }
    }
}
