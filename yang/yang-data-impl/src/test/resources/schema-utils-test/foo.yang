module foo {
    namespace my-namespace;
    prefix p;
    yang-version 1.1;

    feature my-name;

    identity my-name;

    extension my-name;

    typedef my-name {
        type string;
    }

    grouping my-name {
    }

    grouping my-name-2 {
    }

    notification my-name {
        grouping my-name-a {
        }
        container my-name-a {
        }
    }

    container my-name-2 {
        grouping my-name-b {
        }
        notification my-name-b {
        }
        grouping my-name-2-b {
        }
        action my-name-2-b {
        }
    }
}
