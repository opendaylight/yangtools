module test {
    yang-version 1.1;
    namespace "urn:opendaylight:controller:sal:dom:store:test";
    prefix test;

    revision 2014-03-13;

    container root {
        list list-a {
            key "leaf-a";
            leaf leaf-a {
                type string;
            }
            list list-b {
                key "leaf-b";
                leaf leaf-b {
                    type string;
                }
            }
        }

        choice choice {
        }

        leaf leaf {
            type string;
        }

        leaf-list leaf-set {
            type string;
        }

        leaf-list user-leaf-set {
            ordered-by user;
            type string;
        }

        list user-map {
            ordered-by user;
            key "user-map-entry";
            leaf user-map-entry {
                type string;
            }
        }

        list unkeyed-list {
            leaf unkeyed-list-leaf {
                type string;
            }
        }

        anydata any-data {}
    }

    augment "/test:root/test:choice" {
        leaf augment {
            type string;
        }
    }
}
