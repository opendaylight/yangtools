module another {
    yang-version 1.1;
    namespace "urn:opendaylight:controller:sal:dom:store:another";
    prefix another;

    import test { prefix test; }

    augment "/test:root" {
        container another {
            list list-from-another-namespace {
                key "leaf-from-another-namespace";
                leaf leaf-from-another-namespace {
                    type string;
                }
            }
        }
    }
}
