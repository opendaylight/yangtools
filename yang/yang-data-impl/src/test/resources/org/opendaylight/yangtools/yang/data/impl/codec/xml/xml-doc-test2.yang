/*
 * Copyright (c) 2016 Cisco Systems, Inc. and others.  All rights reserved.
 *
 * This program and the accompanying materials are made available under the
 * terms of the Eclipse Public License v1.0 which accompanies this distribution,
 * and is available at http://www.eclipse.org/legal/epl-v10.html
 */
module xml-doc-test-2 {
    yang-version 1;
    namespace "urn:opendaylight:controller:xml:doc:test2";
    prefix "xmldt";

    revision 2014-07-28 {
       description "Initial test";
    }

    container cont2 {

        list l {
            key "id";

            leaf id {
                type string;
            }
        }
    }
}
