module serializer-test {
    yang-version 1;
    namespace "dom-serializer-test";
    prefix "dst";

    revision "2016-01-01" {
        description "Initial revision.";
    }

    typedef int-with-range {
        type int8 {
            range 1..20;
        }
    }

    container root {
        leaf first-leaf {
            type int-with-range;
        }

        leaf-list first-leaf-list  {
            type string;
        }
    }
}
