module immutable-ordered-map-node {
    yang-version 1;
    namespace "test.namespace.builder.test";
    prefix "iomn";

    revision "2016-01-01" {
        description "Initial revision.";
    }

    container root-container {
        list list-ordered-by-user-with-key {
            key "leaf-a";
            ordered-by "user";

            leaf leaf-a {
                type string;
            }
        }

        leaf-list leaf-list-ordered-by-user {
            ordered-by "user";
            type string;
        }
    }
}
