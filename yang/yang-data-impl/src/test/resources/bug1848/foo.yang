module foo {
    namespace "foo";
    prefix "foo";
    revision "2016-02-17";
    container root {
        list policy {
            key name;
            leaf name {
                type string;
            }
            list rule {
                key name;
                leaf name {
                    type string;
                }
            }
        }
    }
}
