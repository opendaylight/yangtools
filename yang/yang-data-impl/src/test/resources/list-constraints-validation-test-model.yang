module list-constraints-validation-test-model  {
    yang-version 1;
    namespace "urn:opendaylight:params:xml:ns:yang:list-constraints-validation-test-model";
    prefix "list-constraints-validation";

    revision "2015-02-02" {
        description "Initial revision.";
    }

    container master-container {
        presence true;
        list min-max-list {
            min-elements 2;
            max-elements 3;

            key "min-max-key-leaf";

            leaf min-max-key-leaf {
                type string;
            }
        }

        list unbounded-list {
            key "unbounded-key-leaf";

            leaf unbounded-key-leaf {
                type int8;
            }
        }

        leaf-list min-max-leaf-list {
            min-elements 1;
            max-elements 3;
            type string;
        }

        leaf-list unbounded-leaf-list {
            type string;
        }

        list unkeyed-list {
            max-elements 1;
            leaf unkeyed-leaf {
                type string;
            }
        }
    }
}
