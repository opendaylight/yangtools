module foo {
    namespace foo;
    prefix foo-mod;

    import bar { prefix bar-imp; revision-date 1970-01-01; }

    leaf my-leaf {
        type foo-leafref;
    }

    typedef foo-leafref {
        type bar-imp:bar-leafref;
        description "foo-leafref";
    }

    leaf my-leaf-2 {
        type foo-leafref-2;
    }

    typedef foo-leafref-2 {
        type bar-imp:bar-base-leafref;
        description "foo-leaf-ref-2";
    }

    leaf bar-base-leafref {
        type bar-imp:bar-base-leafref;
    }

    leaf bar-base-leafref-2 {
        type bar-imp:bar-base-leafref;
        description "bar-base-leafref-2";
    }

    leaf direct-leafref {
        type leafref {
            path "/bar-imp:bar-target";
        }
    }
}
