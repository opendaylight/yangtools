module baz {
    namespace baz;
    prefix baz-mod;

    typedef my-leafref {
        type leafref {
            path "/baz-mod:root/baz-mod:target";
        }
        description "baz-leafref";
    }

    container root {
        leaf target {
            type string;
        }
    }
}
