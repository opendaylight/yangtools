module bug8291 {
    yang-version 1;
    namespace bug8291;
    prefix bug8291;

    container root {
        list outer-list {
            key "id";
            leaf id {
                type uint16;
            }
           list inner-list {
                key name;
                leaf name {
                    type string;
                }
                leaf value {
                    type string;
                }
            }
        }
    }
}
