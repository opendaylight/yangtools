module case-exclusion-test {
    yang-version 1;
    namespace "urn:opendaylight:params:xml:ns:yang:controller:md:sal:dom:store:test";
    prefix "store-test";

    revision "2014-03-13" {
        description "Initial revision.";
    }

    container test {
        presence true;
        config true;
        choice choice1 {
            case case1 {
                leaf case1-leaf1 {
                    type string;
                }
            }
            case case2 {
                container case2-cont {
                    leaf case2-leaf1 {
                        type string;
                    }
                }
            }
        }

        list outer-list {

            key id;
            leaf id {
                type uint16;
            }
            choice outer-choice {
                case one {
                    leaf one {
                        type string;
                    }
                }
                case two-three {
                    leaf two {
                        type string;
                    }
                    leaf three {
                        type string;
                    }
                }
            }
            list inner-list {
                key name;
                leaf name {
                    type string;
                }
                leaf value {
                    type string;
                }
            }

            list inner-list2 {
                key name;
                leaf name {
                    type string;
                }
                leaf value {
                    type string;
                }
            }
        }
    }
}
