module odl-datastore-test {
    yang-version 1;
    namespace "urn:opendaylight:params:xml:ns:yang:controller:md:sal:dom:store:test";
    prefix "store-test";

    revision "2014-03-13" {
        description "Initial revision.";
    }

    container non-presence {
        description "Deep structure of (structural) nodes to test structural ";

        leaf name {
            type string;
        }

        choice deep-choice {
            list a-list {
                key "a-name";

                leaf a-name {
                    type string;
                }
            }

            container b-container {
                leaf b-name {
                    type string;
                }
            }
        }
    }

    container test {
        presence true;
        choice choice1 {
            case case1 {
                leaf case1-leaf1 {
                    type string;
                    config false;
                }
            }
            case case2 {
                container case2-cont {
                    leaf case2-leaf1 {
                        type string;
                        config false;
                    }
                }
            }
        }

        list outer-list {

            key id;
            leaf id {
                type uint16;
            }
            choice outer-choice {
                case one {
                    leaf one {
                        type string;
                    }
                }
                case two-three {
                    leaf two {
                        type string;
                    }
                    leaf three {
                        type string;
                    }
               }
            }
            list inner-list {
                config false;
                key name;
                leaf name {
                    type string;
                }
                leaf value {
                    type string;
                }
            }

            list inner-list2 {
                key name;
                leaf name {
                    type string;
                }
                leaf value {
                    type string;
                    config false;
                }
            }
        }

        container inner-container {
            leaf value {
                type string;
            }
        }
    }
}
