module bar {
    namespace "bar";
    prefix bar;

    container bar {
        container my-container-1 {
            leaf my-leaf-1 {
                type string;
            }
        }

        container my-container-2 {
            leaf my-leaf-2 {
                type string;
            }
        }
    }
}
