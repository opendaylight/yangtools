module foo {
    namespace "foo";
    prefix foo;

    container my-container-1 {
        leaf my-leaf-1 {
            type string;
        }
    }

    container my-container-2 {
        container inner-container {
            leaf my-leaf-2 {
                type string;
            }
        }
        leaf my-leaf-3 {
            type string;
        }
    }

    anyxml my-anyxml-data {
        foo:anyxml-schema-location "/my-container-2";
    }

    extension anyxml-schema-location {
        argument schema-path;
    }
}
