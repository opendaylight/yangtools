/*
 * Copyright (c) 2016 Cisco Systems, Inc. and others.  All rights reserved.
 *
 * This program and the accompanying materials are made available under the
 * terms of the Eclipse Public License v1.0 which accompanies this distribution,
 * and is available at http://www.eclipse.org/legal/epl-v10.html
 */
module test {
    yang-version 1;
    namespace "urn:opendaylight:test";
    prefix "test";

    organization "Cisco Systems, Inc.";

    revision "2014-03-13" {
        description
            "Initial revision";
    }

    container cont{
        leaf l {
            type string;
        }
    }
}
