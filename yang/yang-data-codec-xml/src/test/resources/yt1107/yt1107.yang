module yt1107 {
    namespace "yt1107";
    prefix "yt1107";
    container parent {
        config true;
        list user {
            key name;
            leaf name {
                type string;
            }
        }
        list admin {
            key name;
            leaf name {
                type string;
            }
        }
    }
}
