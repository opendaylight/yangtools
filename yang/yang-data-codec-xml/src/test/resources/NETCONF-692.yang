module test2 {
    namespace "testenv:idea:test2";
    prefix "tt";
    container parent {
        config true;
        list user {
            key name;
            leaf name {
                type string;
            }
        }
        list admin {
            key name;
            leaf name {
                type string;
            }
        }
    }
}
