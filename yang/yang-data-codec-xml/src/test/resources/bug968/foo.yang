module test-leafref {
    yang-version 1.1;
    namespace test-leafref;
    prefix lr;

    leaf leaf-leafref-deref {
        type leafref {
            path "deref(../cont)/cont-leaf";
        }
    }

    container cont {
        leaf cont-leaf {
            type int32;
        }
    }
}
