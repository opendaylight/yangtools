module a {
  yang-version 1;
  namespace "a";
  prefix "a";

  grouping foo_grp {
    leaf key_leaf1 {
      type leafref {
        path "../../a:foo_cont/a:name";
      }
    }
  }
  container bar_cont {
    leaf leaf2 {
       type leafref {
        path "../../../a:foo_cont/a:name";
      }
    }
  }
}
