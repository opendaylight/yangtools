module opendaylight-md-sal-dom {
    yang-version 1;
    namespace "urn:opendaylight:params:xml:ns:yang:controller:md:sal:dom";
    prefix "md-sal-dom";

    import config { prefix config; revision-date 2013-04-05; }

    description
        "Service definition for Binding Aware MD-SAL.";

    revision "2013-10-28" {
        description
                "Initial revision";
    }

    identity dom-broker-osgi-registry {
        base "config:service-type";
        config:java-class "org.opendaylight.controller.sal.core.api.Broker";
    }

    identity dom-async-data-broker {
        base "config:service-type";
        config:java-class "org.opendaylight.controller.md.sal.dom.api.DOMDataBroker";
    }

    identity schema-service {
        base "config:service-type";
        config:java-class "org.opendaylight.controller.sal.core.api.model.SchemaService";
    }
}
