module opendaylight-operational-dom-datastore {
    yang-version 1;
    namespace "urn:opendaylight:params:xml:ns:yang:controller:md:sal:core:spi:operational-dom-store";
    prefix "operational-dom-store-spi";

    import config { prefix config; revision-date 2013-04-05; }

    description
        "DOM Service Provider Interface definition for MD-SAL operational
        store";

    revision "2014-06-17" {
        description
                "Initial revision";
    }

    identity operational-dom-datastore {
        base "config:service-type";
        config:java-class "org.opendaylight.controller.sal.core.spi.data.DOMStore";
    }

}
