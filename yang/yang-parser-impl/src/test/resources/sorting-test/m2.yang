//
// Copyright (c) 2013 Cisco Systems, Inc. and others.  All rights reserved.
//
// This program and the accompanying materials are made available under the
// terms of the Eclipse Public License v1.0 which accompanies this distribution,
// and is available at http://www.eclipse.org/legal/epl-v10.html
//
module m2 {

    yang-version 1;
    namespace "urn:test.m2";
    prefix "m2";

    revision 2014-01-13 {
    }

}
