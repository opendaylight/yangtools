module foobar {
    namespace "foobar";
    prefix foobar;
    yang-version 1;

    import semantic-version { prefix sv; sv:semantic-version "2.1.950"; }

    revision "2016-01-31" {
        description "Not-imported version";
    }
    sv:semantic-version "8.0.0";

    container root {
        leaf included-not-correct-mark {
            type empty;
        }
        container test-container {
        }
    }
}
