module invalid-11 {
    namespace "invalid-11";
    prefix v;
    yang-version 1.1;

    container root {
        rpc root-rpc {
            input {
            }
            output {
            }
        }
    }
}
