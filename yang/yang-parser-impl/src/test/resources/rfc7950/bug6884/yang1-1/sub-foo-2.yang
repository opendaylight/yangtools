submodule sub-foo-2 {
    yang-version 1.1;

    belongs-to foo {
        prefix foo;
    }

    grouping sub-foo-2-grp {
        container sub-foo-2-con {
        }
    }

    container sub-root-2 {
    }
}
