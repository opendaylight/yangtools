submodule sub-foo {
    belongs-to foo {
        prefix foo;
    }

    include sub-foo-2;

    revision 2017-02-09;

    grouping sub-foo-grp {
        container sub-foo-con {
        }
    }

    container sub-root {
        uses sub-foo-2-grp;
    }
}
