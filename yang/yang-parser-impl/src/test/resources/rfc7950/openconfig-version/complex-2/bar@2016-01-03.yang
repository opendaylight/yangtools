module bar {
    namespace "bar";
    prefix bar;
    yang-version 1;

    import openconfig-extensions { prefix oc-ext; oc-ext:openconfig-version "2.0.40"; }
    import foobar { prefix foobar; oc-ext:openconfig-version "7.12.54"; }

    revision "2016-01-03" {
        description "Imported version";
    }
    oc-ext:openconfig-version "4.9.8";

    augment "/foobar:root/foobar:test-container" {
        leaf should-present-leaf-1 {
            type string;
        }
        leaf should-present-leaf-2 {
            type uint8;
            default 0;
        }
    }
}
