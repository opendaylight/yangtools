module foobar {
    namespace "foobar";
    prefix foobar;
    yang-version 1;

    import openconfig-extensions { prefix oc-ext; oc-ext:openconfig-version "2.5.50"; }

    revision "2016-02-28" {
        description "Imported version";
    }
    oc-ext:openconfig-version "7.13.99";

    container root {
        leaf included-correct-mark {
            type empty;
        }
        container test-container {
        }
    }
}
