module invalid-foo-10-bit {
    namespace "foo";
    prefix foo;

    feature f;

    typedef bits-typedef {
        type bits {
            bit one;
            bit two {
                if-feature f;
            }
            bit three;
        }
    }

    typedef bits-typedef-2 {
        type bits-typedef;
        default three;
    }

    leaf bit-leaf {
        type bits-typedef-2;
    }
}
