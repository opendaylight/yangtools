module invalid-foo-enum-2 {
    namespace "foo";
    prefix foo;
    yang-version 1.1;

    feature f;

    leaf enum-leaf {
        type enumeration {
            enum one;
            enum two {
                if-feature f;
            }
            enum three;
        }
        default two;
    }
}
