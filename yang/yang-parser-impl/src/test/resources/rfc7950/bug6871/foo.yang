module foo {
    namespace foo-namespace;
    prefix foo-prefix;
    yang-version 1.1;

    revision 2016-12-14;

    notification my-notification {
        must "foo != bar";
        must "a = b";
    }

    rpc my-rpc {
        input {
            must "bar = foo";
            must "c != d";
        }

        output {
            must "baz != bar";
            must "x = y";
        }
    }
}
