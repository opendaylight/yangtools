module foo {
    namespace foo;
    prefix foo;

    import bar {
        prefix bar;
        revision-date 2017-01-20;
    }

    revision 2017-01-20;

    deviation "/bar:invalid/bar:path" {
        deviate not-supported;
    }

    container my-cont {

    }
}
