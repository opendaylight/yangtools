module foo {
    namespace foo;
    prefix foo;
    yang-version 1.1;

    import bar {
        prefix bar;
        revision-date 2017-01-20;
    }

    revision 2017-01-20;

    deviation "/bar:my-leaf-list" {
        deviate add {
            config false;
            min-elements 5;
            max-elements 10;
            default 100;
            default 200;
            units "hours";
        }
    }

    deviation "/bar:my-list" {
        deviate add {
            unique "my-leaf-a my-leaf-b";
            unique "my-leaf-c my-leaf-d";
        }
    }

    deviation "/bar:my-choice" {
        deviate add {
            default c2;
        }
    }

    deviation "/bar:my-rpc/bar:input" {
        deviate add {
            must "day or night";
            must "black and white";
        }
    }

    deviation "/bar:my-rpc/bar:output" {
        deviate add {
            must "day or night";
            must "black and white";
        }
    }

    deviation "/bar:my-notification" {
        deviate add {
            must "day or night";
            must "black and white";
        }
    }

    deviation "/bar:my-anyxml" {
        deviate add {
            mandatory true;
            foo:custom-property "arg";
            foo:custom-property "another arg";
        }
    }

    extension custom-property {
        argument name;
    }
}
