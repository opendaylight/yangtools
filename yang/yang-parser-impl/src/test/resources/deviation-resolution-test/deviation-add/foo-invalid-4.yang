module foo {
    namespace foo;
    prefix foo;

    import bar {
        prefix bar;
        revision-date 2017-02-01;
    }

    revision 2017-02-01;

    deviation "/bar:my-cont/bar:my-used-leaf" {
        deviate add {
            default 50;
        }
    }
}
