module foo {
    namespace foo;
    prefix foo;

    revision 2017-01-20;

    deviation "/my-leaf" {
        deviate delete {
            config false;
        }
    }

    leaf my-leaf {
        type int32;
        config false;
    }
}
