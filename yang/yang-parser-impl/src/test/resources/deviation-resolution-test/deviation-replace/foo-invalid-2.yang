module foo {
    namespace foo;
    prefix foo;
    yang-version 1.1;

    revision 2017-01-20;

    deviation "/my-leaf-list" {
        deviate replace {
            default "new default value";
        }
    }

    leaf-list my-leaf-list {
        type string;
        default "default value one";
        default "default value two";
    }
}
