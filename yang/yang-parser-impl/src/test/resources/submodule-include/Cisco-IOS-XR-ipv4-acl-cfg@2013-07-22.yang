module Cisco-IOS-XR-ipv4-acl-cfg {

  /*** NAMESPACE / PREFIX DEFINITION ***/

  namespace "http://cisco.com/ns/yang/Cisco-IOS-XR-ipv4-acl-cfg";


  prefix "ipv4-acl-cfg";

  /*** LINKAGE (IMPORTS / INCLUDES) ***/

  import ietf-inet-types { prefix "inet"; }

  import Cisco-IOS-XR-types { prefix "xr"; }

  import Cisco-IOS-XR-ipv4-acl-datatypes { prefix "dt1"; }

  include Cisco-IOS-XR-ipv4-ace-cfg {
    revision-date 2013-07-22;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-acl package configuration.

     This module contains definitions
     for the following management objects:
       ipv4-acl-and-prefix-list: IPv4 ACL configuration data

     Copyright (c) 2013 by Cisco Systems, Inc.
     All rights reserved.";

  revision "2013-07-22" {
    description
      "Initial revision.";
  }


  container ipv4-acl-and-prefix-list {
    xr:xr-xml-map "ipv4_acl_cfg:IPV4_ACLAndPrefixList";
    description "IPv4 ACL configuration data";

    container accesses {
      xr:xr-xml-map "ipv4_acl_cfg:AccessListTable";
      description
        "Table of access lists.  Entries in this table
        and the AccessListExistenceTable table must be
        kept consistent";

      list access {
        xr:xr-xml-map "ipv4_acl_cfg:AccessList";
        key "access-list-name";
        description "An ACL";

        container access-list-entries {
          xr:xr-xml-map "ipv4_acl_cfg:AccessListEntryTable";
          description "ACL entry table; contains list of ACEs";

          list access-list-entry {
            xr:xr-xml-map "ipv4_acl_cfg:AccessListEntry";
            xr:xr-cli-map "(<number>) <enum> (ip)|(ipv4)|(<enum>) ";
            key "sequence-number";
            description
              "An ACL entry; either a description (remark)
              or an ACE to match against";
            leaf sequence-number {
              xr:xr-xml-map "ipv4_acl_cfg:SequenceNumber";
              type dt1:Ipv4-acl-sequence-number-range;
              description "Sequence number for this entry";
            }
            uses IPV4-ACE;
          }
        }
        leaf access-list-name {
          xr:xr-xml-map "ipv4_acl_cfg:AccessListName";
          type string;
          description "Access list name - 64 characters max";
        }
      }
    }

    container prefixes {
      xr:xr-xml-map "ipv4_acl_cfg:PrefixListTable";
      description
        "Table of ACL prefix lists.  Entries in this
        table and the PrefixListExistenceTable table
        must be kept consistent";

      list prefix {
        xr:xr-xml-map "ipv4_acl_cfg:PrefixList";
        key "prefix-list-name";
        description "Name of a prefix list";

        container prefix-list-entries {
          xr:xr-xml-map "ipv4_acl_cfg:PrefixListEntryTable";
          description "Sequence of entries forming a prefix list";

          list prefix-list-entry {
            xr:xr-xml-map "ipv4_acl_cfg:PrefixListEntry";
            xr:xr-cli-map "prefix-list <string> [[seq] <number>] <e"+
              "num> <IP address mask> (eq <number>)|((ge <number>)|"+
              "(le <number>))] ";
            key "sequence-number";
            description
              "A prefix list entry; either a description
              (remark) or a prefix to match against";
            leaf sequence-number {
              xr:xr-xml-map "ipv4_acl_cfg:SequenceNumber";
              type dt1:Ipv4-acl-sequence-number-range;
              description "Sequence number of prefix list";
            }
            leaf grant {
              xr:xr-xml-map "ipv4_acl_cfg:Grant";
              type dt1:Ipv4-acl-grant-enum;
              description
                "Whether to forward or drop packets matching
                the prefix list";
            }
            leaf prefix {
              xr:xr-xml-map "ipv4_acl_cfg:Prefix";
              type inet:ipv4-address;
              description "IPv4 address prefix to match";
            }
            leaf netmask {
              xr:xr-xml-map "ipv4_acl_cfg:Netmask";
              type inet:ipv4-address;
              description "Mask of IPv4 address prefix";
            }
            leaf match-exact-length {
              xr:xr-xml-map "ipv4_acl_cfg:MatchExactLength";
              type empty;
              description
                "Set to perform an exact prefix length match.
                Item is mutually exclusive with minimum and
                maximum length match items";
            }
            leaf exact-prefix-length {
              xr:xr-xml-map "ipv4_acl_cfg:ExactPrefixLength";
              type dt1:Ipv4-acl-prefix-length-range;
              description
                "If exact prefix length matching specified,
                set the length of prefix to be matched";
            }
            leaf match-max-length {
              xr:xr-xml-map "ipv4_acl_cfg:MatchMaxLength";
              type empty;
              description
                "Set to perform a maximum length prefix match
                .  Item is mutually exclusive with exact
                length match item";
            }
            leaf max-prefix-length {
              xr:xr-xml-map "ipv4_acl_cfg:MaxPrefixLength";
              type dt1:Ipv4-acl-prefix-length-range;
              description
                "If maximum length prefix matching specified,
                set the maximum length of prefix to be
                matched";
            }
            leaf match-min-length {
              xr:xr-xml-map "ipv4_acl_cfg:MatchMinLength";
              type empty;
              description
                "Set to perform a minimum length prefix match
                .  Item is mutually exclusive with exact
                length match item";
            }
            leaf min-prefix-length {
              xr:xr-xml-map "ipv4_acl_cfg:MinPrefixLength";
              type dt1:Ipv4-acl-prefix-length-range;
              description
                "If minimum length prefix matching specified,
                set the minimum length of prefix to be
                matched";
            }
            leaf remark {
              xr:xr-xml-map "ipv4_acl_cfg:Remark";
              type string;
              description
                "Comments or a description for the prefix
                list.  Item is mutually exclusive with all
                others in the object";
            }
          }
        }
        leaf prefix-list-name {
          xr:xr-xml-map "ipv4_acl_cfg:PrefixListName";
          type string;
          description "Prefix list name - max 32 characters";
        }
      }
    }

    container log-update {
      xr:xr-xml-map "ipv4_acl_cfg:LogUpdate";
      description "Control access lists log updates";
      leaf threshold {
        xr:xr-xml-map "ipv4_acl_cfg:Threshold";
        xr:xr-cli-map "access-list log-update threshold <number> ";
        type dt1:Ipv4-acl-log-threshold-range;
        description "Log update threshold (number of hits)";
      }
      leaf rate {
        xr:xr-xml-map "ipv4_acl_cfg:Rate";
        xr:xr-cli-map "access-list log-update rate <number> ";
        type dt1:Ipv4-acl-log-rate-range;
        description "Log update rate (log msgs per second)";
      }
    }
  }
}
