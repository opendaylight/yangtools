submodule Cisco-IOS-XR-ipv4-ace-cfg {
    
  belongs-to Cisco-IOS-XR-ipv4-acl-cfg {
    prefix ipv4-acl-cfg;
  }
  
  import Cisco-IOS-XR-ipv4-acl-datatypes {
    prefix "ipv4-acl-dt";
  }

  import ietf-inet-types { 
    prefix "inet";
  }
    
  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR IPv4 ACL entry configuration.

     Copyright (c) 2013 by Cisco Systems, Inc.
     All rights reserved.";

  revision "2013-07-22" {
    description
      "Initial revision.";
  }
   
  typedef Next-hop-type {
    type enumeration {
      enum none-next-hop {
        description "None next-hop.";
      }
      enum regular-next-hop {
        description "Regular next-hop.";
      }
      enum default-next-hop {
        description "Default next-hop.";
      }
    }
    description "Next-hop type.";
  }

  grouping IPV4-ACE {
    description "IPv4 ACL entry.";
    leaf grant {
      type ipv4-acl-dt:Ipv4-acl-grant-enum;
      description "Whether to forward or drop packets matching the 
                   ACE.";
    }

    leaf protocol {
      type ipv4-acl-dt:Ipv4-acl-protocol-number;
      description "Protocol to match.";
    }

    container source-network {
      description "Source network settings.";
      leaf source-address {
        type inet:ipv4-address;
        description "Source IPv4 address to match, leave unspecified
                     for any.";
      }
      leaf source-wild-card-bits {
        type inet:ipv4-address;
        description "Wildcard bits to apply to source address 
                     (if specified), leave unspecified for no 
                     wildcarding.";
      }
    }

    container destination-network {
      description "Destination network settings.";
      leaf destination-address {
        type inet:ipv4-address;
        description "Destination IPv4 address to match (if a protocol
                     was specified), leave unspecified for any.";
      }
      leaf destination-wild-card-bits {
        type inet:ipv4-address;
        description "Wildcard bits to apply to destination address
                     (if specified), leave unspecified for no 
                     wildcarding.";
      }
    }

    container source-port {
      when "../protocol = '6' or ../protocol = '17' or "+
           "../protocol = '132'" {
        description "Applicable only to TCP, SCTP and UDP.";
      }
      description "Source port settings.";
      leaf source-operator {
        type ipv4-acl-dt:Ipv4-acl-operator-enum;
        description "Source comparison operator . Leave unspecified 
                     if no source port comparison is to be done.";
      }
      leaf first-source-port {
        type ipv4-acl-dt:Ipv4-acl-port-number;
        description "First source port for comparison, leave 
                     unspecified if source port comparison is not to
                     be performed.";
      }
      leaf second-source-port {
        type ipv4-acl-dt:Ipv4-acl-port-number;
        description "Second source port for comparion, leave 
                     unspecified if source port comparison is not to
                     be performed.";
      }
    }
    
    container destination-port {
      when "../protocol = '6' or ../protocol = '17' or "+
           "../protocol = '132'" {
        description "Applicable only to TCP, SCTP and UDP.";
      }
      description "Destination port settings.";
      leaf destination-operator {
        type ipv4-acl-dt:Ipv4-acl-operator-enum;
        description "Destination comparison operator. Leave 
                     unspecified if no destination port comparison is
                     to be done.";
      }
      leaf first-destination-port {
        type ipv4-acl-dt:Ipv4-acl-port-number;
        description "First destination port for comparison, leave
                     unspecified if destination port comparison is
                     not to be performed.";
      }
      leaf second-destination-port {
        type ipv4-acl-dt:Ipv4-acl-port-number;
        description "Second destination port for comparion, leave
                     unspecified if destination port comparison is
                     not to be performed.";
      }
    }
    
    container icmp {
      when "../protocol = '1'" {
        description "Applicable only to ICMP.";
      }
      description "ICMP settings.";
      leaf icmp-type-code {
        type ipv4-acl-dt:Ipv4-acl-icmp-type-code-enum;
        description "Well known ICMP message code types to match, 
                     leave unspecified if ICMP message code type 
                     comparion is not to be performed.";
      }
    }
    
    container tcp {
      when "../protocol = '6'" {
        description "Applicable only to TCP.";
      }
      description "TCP settings.";
      leaf tcp-bits-match-operator {
        type ipv4-acl-dt:Ipv4-acl-tcp-match-operator-enum;
        description "TCP Bits match operator. Leave unspecified if 
                     flexible comparison of TCP bits is not 
                     required.";
      }
      leaf tcp-bits {
        type ipv4-acl-dt:Ipv4-acl-tcp-bits-number;
        description "TCP bits to match.
                     Leave unspecified if comparison of TCP bits is
                     not required.";
      }
      leaf tcp-bits-mask {
        type ipv4-acl-dt:Ipv4-acl-tcp-bits-number;
        description "TCP bits mask to use for flexible TCP matching.
                     Leave unspecified if tcp-bits-match-operator is 
                     unspecified.";
      }
    }
    
    container packet-length {
      description "Packet length settings.";
      leaf packet-length-operator {
        type ipv4-acl-dt:Ipv4-acl-operator-enum;
        description "Packet length operator applicable if Packet 
                     length is to be compared. Leave unspecified if 
                     no packet length comparison is to be done.";
      }
      leaf packet-length-min {
        type ipv4-acl-dt:Ipv4-acl-plen-range;
        description "Minimum packet length for comparison, leave 
                     unspecified if packet length comparison is not 
                     to be performed or if only the maximum packet 
                     length should be considered.";
      }
      leaf packet-length-max {
        type ipv4-acl-dt:Ipv4-acl-plen-range;
        description "Maximum packet length for comparion, leave 
                     unspecified if packet length comparison is not 
                     to be performed or if only the minimum packet 
                     length should be considered.";
      }
    }
    
    container time-to-live {
      description "TTL settings.";
      leaf time-to-live-operator {
        type ipv4-acl-dt:Ipv4-acl-operator-enum;
        description "TTL operator is applicable if TTL is to be 
                     compared. Leave unspecified if TTL 
                     classification is not required.";
      }
      leaf time-to-live-min {
        type ipv4-acl-dt:Ipv4-acl-ttl-range;
        description "TTL value for comparison OR Minimum TTL value 
                     for TTL range comparision, leave unspecified if
                     TTL classification is not required.";
      }
      leaf time-to-live-max {
        type ipv4-acl-dt:Ipv4-acl-ttl-range;
        description "Maximum TTL for comparion, leave unspecified if 
                     TTL comparison is not to be performed or if only
                     the minimum TTL should be considered.";
      }
    }

    container next-hop {
      description "Next-hop settings.";
      leaf next-hop-type {
        type Next-hop-type;
        description "The nexthop type.";
      }
      container next-hop-1 {
        description "The first next-hop settings.";
        leaf next-hop {
          type inet:ipv4-address;
          description "The IPv4 address of the next-hop.";
        }
        leaf vfr-name {
          type string;
          description "The VRF name of the next-hop.";
        }
        leaf track-name {
          type string;
          description "The object tracking name for the next-hop.";
        }
      }
      container next-hop-2 {
        description "The second next-hop settings.";
        leaf next-hop {
          type inet:ipv4-address;
          description "The IPv6 address of the next-hop.";
        }
        leaf vfr-name {
          type string;
          description "The VRF name of the next-hop.";
        }
        leaf track-name {
          type string;
          description "The object tracking name for the next-hop.";
        }
      }
      container next-hop-3 {
        description "The third next-hop settings.";
        leaf next-hop {
          type inet:ipv4-address;
          description "The IPv6 address of the next-hop.";
        }
        leaf vfr-name {
          type string;
          description "The VRF name of the next-hop.";
        }
        leaf track-name {
          type string;
          description "The object tracking name for the next-hop.";
        }
      }
    }
    
    leaf counter-name {
      type string;
      description "Counter name.";
    }

    leaf igmp-message-type {
      when "../protocol = '2'" {
        description "Applicable only to IGMP.";
      }
      type ipv4-acl-dt:Ipv4-acl-igmp-number;
      description "IGMP message type to match. Leave unspecified if 
                   no message type comparison is to be done.";
    }

    leaf dscp {
      type ipv4-acl-dt:Ipv4-acl-dscp-number;
      description "DSCP value to match leave unspecified if DSCP 
                   comparion is not to be performed.";
    }

    leaf precedence {
      type ipv4-acl-dt:Ipv4-acl-precedence-number;
      description "Precedence value to match (if a protocol was 
                   specified), leave unspecified if precedence 
                   comparion is not to be performed.";
    }

    leaf log-option {
      type ipv4-acl-dt:Ipv4-acl-logging-enum;
      description "Whether and how to log matches against this 
                   entry.";
    }

    leaf capture {
      type boolean;
      description "Enable capture.";
    }

    leaf icmp-off {
      type empty;
      description "To turn off ICMP generation for deny ACEs.";
    }

    leaf fragments {
      when "../protocol = '1' or ../protocol = '2' "+
           "or ../protocol = '6' or ../protocol = '17' "+
           "or ../protocol = '132'" {
        description "Applicable only to TCP, SCTP, UDP, IGMP and
                     ICMP.";
      }
      type empty;
      description "Check non-initial fragments. Item is mutually 
                   exclusive with TCP, SCTP, UDP, IGMP and ICMP 
                   comparions and with logging.";
    }

    leaf remark {
      type string;
      description "Comments or a description for the access list.";
    }

  } 
}
