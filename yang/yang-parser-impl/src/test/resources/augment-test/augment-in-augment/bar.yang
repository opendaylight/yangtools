module bar {
    yang-version 1;
    namespace "urn:opendaylight.bar";
    prefix "bar";

    organization "opendaylight";
    contact "http://www.opendaylight.org/";

    revision "2013-10-14" {
        reference " WILL BE DEFINED LATER";
    }

    extension opendaylight {
        argument "name" {
            yin-element "true";
        }
    }

    container interfaces {
        grouping ifEntry {
            container augment-holder;
        }
        list ifEntry {
            key "ifIndex";

            leaf ifIndex {
                type uint32;
                units minutes;
            }

            leaf ifMtu {
                type int32;
            }

            min-elements 1;
            max-elements 11;
        }
    }

    container controller {
        choice switch {
            case start {
                leaf start {
                    type int8;
                }
            }
            case stop {
                leaf stop {
                    type int16;
                }
            }
        }
    }

}
