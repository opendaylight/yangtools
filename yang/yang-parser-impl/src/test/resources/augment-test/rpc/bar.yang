//
// Copyright (c) 2013 Cisco Systems, Inc. and others.  All rights reserved.
//
// This program and the accompanying materials are made available under the
// terms of the Eclipse Public License v1.0 which accompanies this distribution,
// and is available at http://www.eclipse.org/legal/epl-v10.html
//
module bar {
    yang-version 1;
    namespace "urn:opendaylight:bar";
    prefix "bar";

    revision "2013-10-11" {
    }

    rpc cancel {
        input {
            leaf id {
                type string;
            }
        }
        output {
            leaf failure {
                type string;
            }
        }
    }


    rpc submit {
        input {
            leaf id {
                type string;
            }
            leaf type {
                type string;
            }
            choice arguments {
            }
        }

        output {
            choice result {
                case failure {
                    leaf failure {
                        type string;
                    }
                }
            }
        }
    }

}
