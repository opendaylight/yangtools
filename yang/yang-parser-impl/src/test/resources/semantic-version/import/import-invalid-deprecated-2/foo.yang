module foo {
    namespace "foo";
    prefix foo;
    yang-version 1;

    import semantic-version { prefix sv; revision-date 2016-02-02; sv:semantic-version "0.9.9"; }

    revision "2016-02-01" {
        description "Initial version";
    }

    container root {
    }
}
