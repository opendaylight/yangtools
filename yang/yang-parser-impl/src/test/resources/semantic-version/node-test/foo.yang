module foo {
    namespace "foo";
    prefix foo;
    yang-version 1;

    import semantic-version { prefix sv; revision-date 2016-02-02; sv:semantic-version "0.0.1"; }
    import bar { prefix bar; revision-date 2017-04-06; sv:semantic-version "2016.4.5"; }

    revision 2016-01-01 {
        description "test";
    }
    
    sv:semantic-version "2016.1.1";

    container foo-root {
        uses bar:grp;
    }
}
