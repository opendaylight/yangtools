module bar {
    sv:semantic-version "0.1.2";

    namespace "bar";
    prefix bar;
    yang-version 1;

    import semantic-version { prefix sv; revision-date 2016-02-02; sv:semantic-version "0.0.1"; }

    revision "2016-01-31" {
        description "Initial version";
    }

    container root {
    }
}
