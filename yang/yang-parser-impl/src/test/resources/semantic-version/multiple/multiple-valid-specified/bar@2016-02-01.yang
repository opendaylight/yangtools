module bar {
    namespace "bar";
    prefix bar;
    yang-version 1;

    import semantic-version { prefix sv; revision-date 2016-02-02; sv:semantic-version "0.0.1"; }

    revision "2016-02-01" {
        description "Initial version";
    }
    sv:semantic-version "5.5.5";

    container root {
    }
}
