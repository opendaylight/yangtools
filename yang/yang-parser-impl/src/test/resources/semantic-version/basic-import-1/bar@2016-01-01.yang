module bar {
    namespace "bar";
    prefix bar;
    yang-version 1;

    import semantic-version { prefix sv; revision-date 2016-02-02; sv:module-version "0.0.1"; }

    revision "2016-01-01" {
        description "Initial version";
    }
    sv:module-version "0.1.2";

    container root {
    }
}
