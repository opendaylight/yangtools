module foo {
    namespace "foo";
    prefix foo;
    yang-version 1;

    import semantic-version { prefix sv; sv:semantic-version "2.5.40"; }
    import bar { prefix bar; sv:semantic-version "4.1.1"; }

    revision "2016-02-01" {
        description "Initial version";
    }
    sv:semantic-version "2.32.2";
}
