module foobar {
    namespace foobar;
    prefix foobar;

    import ietf-restconf {
        prefix rc;
        revision-date 2017-01-26;
    }

    revision 2017-06-01;

    rc:yang-data "my-yang-data" {
        container cont {
            if-feature feat;

            container inner-cont {
                if-feature feat;
            }

            uses grp {
                if-feature feat;
            }
        }
    }

    grouping grp {
        container grp-cont {}
    }
}
