//
// Copyright (c) 2013 Cisco Systems, Inc. and others.  All rights reserved.
//
// This program and the accompanying materials are made available under the
// terms of the Eclipse Public License v1.0 which accompanies this distribution,
// and is available at http://www.eclipse.org/legal/epl-v10.html
//
module test4 {
    yang-version 1;
    namespace "urn:simple.container.demo";
    prefix "t1";

    grouping tree {
        leaf-list node {
            type string;
        }
        container holder {
        
        }
    }

    container schema {
        uses tree {
            refine node {
                presence "true";
            }
            refine holder {
                default "one";
            }
        }
    }

}
