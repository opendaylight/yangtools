//
// Copyright (c) 2013 Cisco Systems, Inc. and others.  All rights reserved.
//
// This program and the accompanying materials are made available under the
// terms of the Eclipse Public License v1.0 which accompanies this distribution,
// and is available at http://www.eclipse.org/legal/epl-v10.html
//
module testfile7 {
    yang-version 1;
    namespace "urn:simple.test7.demo";
    prefix "t7";

    import testfile8 {
        prefix "t8";
        revision-date 2013-08-03;
    }

    organization "opendaylight";
    contact "http://www.opendaylight.org/";

    revision "2013-08-03" {
        reference " WILL BE DEFINED LATER";
    }

    augment "/t8:interfaces/t8:ifEntry" {
        when "if:leafType='ds1'";
        leaf linkleaf {
            mandatory true;
            type binary;
        }
    }

}
