//
// Copyright (c) 2013 Cisco Systems, Inc. and others.  All rights reserved.
//
// This program and the accompanying materials are made available under the
// terms of the Eclipse Public License v1.0 which accompanies this distribution,
// and is available at http://www.eclipse.org/legal/epl-v10.html
//
module testfile8 {
    yang-version 1;
    namespace "urn:simple.test8.demo";
    prefix "t8";

    organization "opendaylight";
    contact "http://www.opendaylight.org/";
    description "This is types-data test description";

    revision "2013-08-03" {
        reference " WILL BE DEFINED LATER";
    }

    container interfaces {
        grouping ifEntry {
            container augment-holder;
        }
        list ifEntry {
            key "ifIndex";
            leaf ifIndex {
                type uint32;
                units minutes;
            }
        }
    }

}
