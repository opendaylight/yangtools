//
// Copyright (c) 2013 Cisco Systems, Inc. and others.  All rights reserved.
//
// This program and the accompanying materials are made available under the
// terms of the Eclipse Public License v1.0 which accompanies this distribution,
// and is available at http://www.eclipse.org/legal/epl-v10.html
//
module augment0 {
    yang-version 1;
    namespace "urn:simple.augment0.demo";
    prefix "a0";

    container foo {
        description "foo container";
        container bar {
            leaf id {
                type int8;
            }
            typedef int-ext {
                type int8 {
                    range "5..10";
                }
            }
            choice choice-ext {
                leaf delta {
                    type int8;
                }
            }
        }
    }

}
