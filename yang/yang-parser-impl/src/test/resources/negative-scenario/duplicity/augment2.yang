//
// Copyright (c) 2013 Cisco Systems, Inc. and others.  All rights reserved.
//
// This program and the accompanying materials are made available under the
// terms of the Eclipse Public License v1.0 which accompanies this distribution,
// and is available at http://www.eclipse.org/legal/epl-v10.html
//
module augment2 {
    yang-version 1;
    namespace "urn:simple.augment2.demo";
    prefix "a2";

    import augment0 {
        prefix "a0";
    }

    augment "/a0:foo/a0:bar/a0:choice-ext" {
        anyxml delta;
    }

}
