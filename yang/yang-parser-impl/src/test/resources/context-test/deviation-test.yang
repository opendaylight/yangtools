//
// Copyright (c) 2013 Cisco Systems, Inc. and others.  All rights reserved.
//
// This program and the accompanying materials are made available under the
// terms of the Eclipse Public License v1.0 which accompanies this distribution,
// and is available at http://www.eclipse.org/legal/epl-v10.html
//
module deviation-test {
    yang-version 1;
    namespace "urn:simple.deviation.test";
    prefix "dev";

    import bar {
        prefix "t";
        revision-date 2013-07-03;
    }

    organization "opendaylight";
    contact "http://www.opendaylight.org/";

    revision "2013-02-27" {
        reference " WILL BE DEFINED LATER";
    }


    deviation /t:interfaces/t:ifEntry {
        deviate add {
            default "admin"; // new users are 'admin' by default
            config "true";
        }
        reference "system/user ref";
    }

}
