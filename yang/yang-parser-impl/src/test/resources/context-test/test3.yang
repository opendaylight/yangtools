//
// Copyright (c) 2013 Cisco Systems, Inc. and others.  All rights reserved.
//
// This program and the accompanying materials are made available under the
// terms of the Eclipse Public License v1.0 which accompanies this distribution,
// and is available at http://www.eclipse.org/legal/epl-v10.html
//
module test3 {

    yang-version 1;
    namespace "urn:simple.demo.test3";
    prefix "t3";
    
    import custom-types-test {
        prefix "custom";
    }
    
    organization "opendaylight";
    contact "WILL-BE-DEFINED-LATER";
    revision 2013-06-18 {
    }

    identity pt {
        base custom:service-type;
    }
    
    container network {
        custom:mountpoint point {
        }
        
        description "network-description";
        reference "network-reference";
        status obsolete;
        config true;
        presence "some presence text";
    }

}
