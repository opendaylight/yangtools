//
// Copyright (c) 2013 Cisco Systems, Inc. and others.  All rights reserved.
//
// This program and the accompanying materials are made available under the
// terms of the Eclipse Public License v1.0 which accompanies this distribution,
// and is available at http://www.eclipse.org/legal/epl-v10.html
//
module test1 {

    yang-version 1;
    namespace "urn:simple.demo.test1";
    prefix "t1";

    import test3 {
        prefix "t3";
        revision-date 2013-06-18;
    }

    import test2 {
        prefix "t2";
        revision-date 2013-06-18;
    }

    import test4 {
        prefix "t4";
        revision-date 2013-06-18;
    }

    organization "opendaylight";
    contact "WILL-BE-DEFINED-LATER";
        revision 2013-06-18 {
    }

    augment "/t4:interfaces/t4:ifEntry/t2:augment-holder/t3:schemas" {
        when "if:ifType='ds0'";
        leaf id {
            type string;
        }
    }

}
