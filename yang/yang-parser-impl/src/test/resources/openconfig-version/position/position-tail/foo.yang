module foo {
    namespace "foo";
    prefix foo;
    yang-version 1;

    import openconfig-extensions { prefix oc-ext; revision-date 2017-01-29; oc-ext:openconfig-version "0.0.1"; }

    revision "2016-02-01" {
        description "Initial version";
    }

    container root {
    }

    oc-ext:openconfig-version "0.1.1";
    import bar { prefix bar; revision-date 2016-01-31; oc-ext:openconfig-version "0.1.2";}
}
