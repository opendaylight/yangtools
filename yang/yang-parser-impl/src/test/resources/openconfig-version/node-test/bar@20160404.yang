module bar {
    namespace "bar";
    prefix bar;
    yang-version 1;
    
    import openconfig-extensions { prefix oc-ext; revision-date 2017-01-29; oc-ext:openconfig-version "0.0.1"; }

    revision 2016-04-04 {
        description "test";
    }
    
    oc-ext:openconfig-version "2016.4.4";

    grouping grp {
        container con20160404 {
        }
    }
}
