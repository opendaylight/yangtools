module foo {
    namespace "foo";
    prefix foo;
    yang-version 1;

    import openconfig-extensions { prefix oc-ext; revision-date 2017-01-29; oc-ext:openconfig-version "0.0.1"; }
    import bar { prefix bar; oc-ext:openconfig-version "0.1.2";}

    revision "2016-02-01" {
        description "Initial version";
    }
    oc-ext:openconfig-version "0.1.1";

    container root {
    }
}
