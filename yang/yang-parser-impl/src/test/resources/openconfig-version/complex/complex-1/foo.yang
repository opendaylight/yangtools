module foo {
    namespace "foo";
    prefix foo;
    yang-version 1;

    import openconfig-extensions { prefix oc-ext; oc-ext:openconfig-version "1.0.0"; }
    import bar { prefix bar; oc-ext:openconfig-version "1.2.5"; }

    revision "2016-02-01" {
        description "Initial version";
    }
    oc-ext:openconfig-version "1.50.02";
}
