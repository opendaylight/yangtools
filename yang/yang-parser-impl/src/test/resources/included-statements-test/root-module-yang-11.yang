module root-module-yang-11 {
    yang-version 1.1;
    namespace "urn:opendaylight.org/root-module-yang-11";
    prefix "rtm";

    include child-module-yang-11 {
        description "Test for Yang 1.1 description substatement support";
        reference "RFC 7950: The YANG 1.1 Data Modeling Language";
    }

    leaf new-leaf {
        type new-string-type;
    }

    leaf old-leaf {
        type new-int32-type;
    }
}
