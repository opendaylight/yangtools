module bar {
    namespace bar-namespace;
    prefix bar-prefix;

    import bar-imp {
        prefix bimp;
        revision-date 2016-09-22;
    }

    revision "2016-09-22";

    deviation "/bimp:bar-container-1" {
        deviate add {
            must "a != b";
        }
        bar-prefix:bar-extension;
    }

    deviation "/bimp:bar-container-2" {
        deviate delete {
            must "a = b";
        }
    }

    deviation "/bimp:bar-container-2" {
        deviate add {
            config false;
        }
    }

    deviation "/bimp:bar-container-1/bimp:bar-leaf-1" {
        deviate add {
            default "def-val";
        }
        description "desc";
    }

    deviation "/bimp:bar-container-1/bimp:bar-leaf-1" {
        deviate add {
            config false;
        }
        description "another desc";
    }

    deviation "/bimp:bar-container-2/bimp:bar-leaf-2" {
        deviate add {
            default "def-val";
        }
        reference "ref";
    }

    deviation "/bimp:bar-container-2/bimp:bar-leaf-2" {
        deviate add {
            config false;
        }
        reference "another ref";
    }

    extension bar-extension {}
}
