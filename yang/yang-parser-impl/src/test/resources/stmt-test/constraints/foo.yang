/*
 * Copyright (c) 2015 Cisco Systems, Inc. and others.  All rights reserved.
 *
 * This program and the accompanying materials are made available under the
 * terms of the Eclipse Public License v1.0 which accompanies this distribution,
 * and is available at http://www.eclipse.org/legal/epl-v10.html
 */
module foo {
    yang-version 1;
    namespace "urn:opendaylight.foo";
    prefix "foo";

    revision "2013-10-08" {
    }

    typedef my-decimal-type {
        type decimal64 {
            fraction-digits 6;
            range "1.5..5.5";
        }
    }

    leaf id-decimal64 {
        type decimal64 {
            fraction-digits 4;
            range "1.5..5.5";
        }
    }
}
