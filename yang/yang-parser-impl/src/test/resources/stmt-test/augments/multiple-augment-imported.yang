module multiple-augment-imported {

    namespace "multiple-augment-imported";
    prefix imp;


    container root-container {
        uses grp1 {
            augment container-from-grp1/sub-container-from-grp1 {
                container container-in-uses-augment {
                }
            }
        }
    }

    grouping grp1 {
        container container-from-grp1 {
            container sub-container-from-grp1 {
                uses grp2 {
                    augment container-from-grp2/sub-container-from-grp2 {
                        container augmented-container-in-uses-grp2;
                    }
                }
            }
        }
    }

    grouping grp2 {
        container container-from-grp2 {
            container sub-container-from-grp2 {
            }
        }
        uses grp3;
    }

    grouping grp3 {
        container container-from-grp3 {
        }
    }

    augment /root-container/container-from-grp1/sub-container-from-grp1/container-in-uses-augment {
        container sub-container-from-augment2 {
        }
    }
    
    grouping grp-from-import {
        container container-from-grp-from-import {
            
        }
    }
}
