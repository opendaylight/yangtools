module parser-impl-test2 {
    namespace parser-impl-test2-ns;
    prefix pit2;

    include parser-impl-test2-submod;

    extension ext2 {
    }

    typedef my-int32 {
        type int32;
    }

    leaf leaf-my-int32 {
        type my-int32;
    }

    grouping grp-aug {
        leaf-list ll1 {
            type string;
            ordered-by user;
            config true;
            mandatory true;

            ext2 extension2;
        }
    }

    container cont1 {
        leaf cont1-condition {
            type string;
        }
        must "cont1-condition != 'true'" {
            error-message "error";
        }
    }

    augment /cont1 {
        uses grp-aug;
    }

    anyxml axml;
}
