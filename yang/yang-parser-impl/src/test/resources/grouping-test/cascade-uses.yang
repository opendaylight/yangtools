//
// Copyright (c) 2013 Cisco Systems, Inc. and others.  All rights reserved.
//
// This program and the accompanying materials are made available under the
// terms of the Eclipse Public License v1.0 which accompanies this distribution,
// and is available at http://www.eclipse.org/legal/epl-v10.html
//
module cascade-uses {
    
    namespace "urn:grouping:cascade-uses";
    prefix "cu";

    organization "OPEN DAYLIGHT";
    contact "http://www.opendaylight.org/";

    revision 2013-07-18 {
    }
  
    grouping grouping-U {
        leaf leaf-grouping-U {
            type string;
        }
        uses grouping-V;
        uses grouping-X;
    }

    grouping grouping-V {
        leaf leaf-grouping-V {
            type string;
        }
        container container-grouping-V {
            uses grouping-X;
        }
        uses grouping-Z;
        uses grouping-ZZ;
    }

    grouping grouping-X {
        leaf leaf-grouping-X {
            type string;
        }
        uses grouping-Y;
    }

    grouping grouping-Y {
        leaf leaf-grouping-Y {
            type string;
        }
    }
    
    grouping grouping-Z {
        leaf leaf-grouping-Z {
            type string;
        }
    }
    
    grouping grouping-ZZ {
        leaf leaf-grouping-ZZ {
            type string;
        }
    }    
}
