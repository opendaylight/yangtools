module bar {
    namespace "bar";
    prefix bar;
    yang-version 1;

    revision 2016-04-06 {
        description "test";
    }

    grouping grp {
        container con20160404 {
        }
        container con20160405 {
        }
        container con20160406 {
        }
    }
}
