module bar {
    namespace "bar:ns";
    prefix br;

    revision 2015-20-08 {
        description "Initial version";
    }

    extension leaf;

    leaf leaf {
        type string;
    }

    br:leaf;
}
