module key-simple-and-comp {
	namespace root;
	prefix root;

	list simple {
		key "key1";
		container key1 {
		}
	}

	list comp {
		key "key1 key2 key3";
		container key1 {
        }
		container key2 {
        }
		container key3 {
        }
	}
}
