module foo {
    yang-version 1.1;
    namespace foo;
    prefix foo;

    revision "2018-01-02";

    container foo {
        list foo {
            leaf bar {
                type string;
            }
            key bar;

            action foo {
            }
        }
    }
}
