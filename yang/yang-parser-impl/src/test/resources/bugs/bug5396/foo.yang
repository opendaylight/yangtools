module foo {
    yang-version 1;
    namespace "foo";
    prefix "foo";

    container root {
        leaf my-leaf2 {
            type dataplane-ifname;
        }
    }

    typedef dataplane-ifname {
        type union {
            // Onboard device
            type string {
                pattern "dp[0-9]+o[0-9]+(d[0-9]+)?";
                //configd:pattern-help "<dpFoN>";
            }
            // hotplug slot index
            type string {
                pattern "dp[0-9]+s[0-9]+(f[0-9]+)?(d[0-9]+)?";
                //configd:pattern-help "<dpFsN>";
            }
            // PCI device address
            type string {
                pattern "dp[0-9]+(P[0-9]+)?p[0-9]{1,3}s[0-9]{1,3}(f[0-9]+)?(d[0-9]+)?";
                //configd:pattern-help "<dpFpNsS>";
            }
            // Biosdevname compatiable names. VMware only
            type string {
                pattern "dp[0-9]+p[0-9]+p[0-9]+";
                //configd:pattern-help "<dpFpNpS>";
            }
        }
    }
}
