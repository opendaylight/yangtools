submodule sub-foo-1 {
    belongs-to foo {
        prefix foo;
    }

    import bar-1 { prefix bar; revision-date 2000-01-01; }

    revision 2017-07-07;

    typedef sub-foo-1-type {
        type string;
    }

    container sub-root-1 {
        leaf my-leaf {
            type bar:bar-1-type;
        }
        leaf my-leaf-2 {
            type foo:foo-type;
        }
    }
}
