submodule sub-foo-2 {
    belongs-to foo {
        prefix foo;
    }

    import bar-2 { prefix bar; revision-date 2000-01-02; }

    revision 2017-07-07;

    typedef sub-foo-2-type {
        type string;
    }

    container sub-root-2 {
        leaf my-leaf {
            type bar:bar-2-type;
        }
        leaf my-leaf-2 {
            type foo:foo-type;
        }
    }
}
