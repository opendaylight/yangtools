module bar {
    namespace "bar";
    prefix bar;
    yang-version 1;

    import foo { prefix foo; revision-date 2016-03-04; }

    revision "2016-03-04" {
        description "test";
    }

    augment "/foo:root" {
        container presence-container {
            presence "presence-container";
        }
    }

    augment "/foo:root/bar:presence-container" {
        container non-presence-container {
        }
    }

    augment "/foo:root/bar:presence-container/bar:non-presence-container" {
        leaf mandatory-leaf {
            type string;
            mandatory true;
        }
    }
}
