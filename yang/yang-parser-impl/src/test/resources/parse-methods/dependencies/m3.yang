module m3 {

    yang-version 1;
    namespace "urn:test.m3";
    prefix "m3";

    import m4 {
        prefix "m4";
    }
    import m6 {
        prefix "m6";
    }

     revision 2013-09-30 {
    }

}
