//
// Copyright (c) 2013 Cisco Systems, Inc. and others.  All rights reserved.
//
// This program and the accompanying materials are made available under the
// terms of the Eclipse Public License v1.0 which accompanies this distribution,
// and is available at http://www.eclipse.org/legal/epl-v10.html
//
module unused {

    yang-version 1;
    namespace "urn:test.unused";
    prefix "u";

    import m2 {
        prefix "m2";
    }
    import m3 {
        prefix "m3";
    }

     revision 2012-04-16 {
    }

}
