submodule module1submodule1 {
    yang-version "1.1";
    belongs-to "module1" {
        prefix "module1";
    }

    import module2 {
        prefix "module2";
    }

    revision "2019-05-17" {
    }

    grouping submodule-grouping {
        uses module2:grouping1;

        leaf leaf2 {
            type string;
            module2:ext1 "param1";
        }
    }
}
