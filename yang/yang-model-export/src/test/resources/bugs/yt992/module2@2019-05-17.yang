module module2 {
    yang-version "1.1";
    namespace "urn:example:module2";
    prefix "module2";

    revision "2019-05-17" {
    }

    grouping grouping1 {
        leaf leaf1 {
            type string;
        }
    }

    extension ext1 {
        argument "parameter";
    }
}
