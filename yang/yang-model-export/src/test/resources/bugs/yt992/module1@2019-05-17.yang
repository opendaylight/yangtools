module module1 {
    yang-version "1.1";
    namespace "urn:example:module1";
    prefix "module1";

    include module1submodule1;

    revision "2019-05-17" {
    }

    container cont1 {
        uses submodule-grouping;
    }
}
