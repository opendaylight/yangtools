module must {
    namespace "must";
    prefix mu;
    yang-version 1.1;

    notification n {
        must "1!=0";
    }

    rpc r {
        input {
            must "1!=0";
        }
        output {
            must "1!=0";
        }
    }

    container root {
        presence "This is a presence container.";
        action a {
            input {
                must "1!=0";
            }
            output {
                must "1!=0";
            }
        }
    }
}
