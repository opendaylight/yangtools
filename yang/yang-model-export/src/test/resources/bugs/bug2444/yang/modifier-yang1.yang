module modifier-yang1 {
    namespace modifier-yang1;
    prefix my1;
    yang-version 1;

    leaf my-leaf {
        type string {
            length 0..2 {
                error-message "Error message length";
                error-app-tag "length-out";
            }
            pattern ".*" {
                error-message "Error message pattern";
                error-app-tag "regex-err";
            }
        }
    }
}
