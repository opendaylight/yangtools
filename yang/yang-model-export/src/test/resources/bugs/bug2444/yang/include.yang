module include {
    yang-version 1.1;
    namespace include;
    prefix inc;

    import deviation-target { prefix dev-tgt; revision-date 2017-01-20; reference "import ref"; description "import desc"; }

    include submodule {
        reference "include ref";
        description "include desc";
    }

    reference "module ref";
    description "module desc";

    revision 2017-06-26 {
        description "2017-06-26 revision desc";
        reference "2017-06-26 revision ref";
    }

    revision 2016-06-26 {
        description "2016-06-26 revision desc";
        reference "2016-06-26 revision ref";
    }

    revision 2015-06-26 {
        description "2015-06-26 revision desc";
        reference "2015-06-26 revision ref";
    }

    container root {
    }
}
