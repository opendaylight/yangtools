module bug2180-test-module {
  yang-version 1;

  namespace "urn:opendaylight:params:xml:ns:yang:controller:md:sal:bug2180:test";

  prefix bug2180-test-module;

  revision 2014-10-22 {
    description "creating base model for netmod";
  }

  container top {
    list ordered-list {
      key id;
      ordered-by user;
      leaf id{
        type string;
      }
    }

    leaf-list ordered-leaf-list {
      type string;
      ordered-by user;      
    }
  }
}
