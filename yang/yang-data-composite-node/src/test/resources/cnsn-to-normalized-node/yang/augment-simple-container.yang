module augment-container-yang {
  namespace "augment:container:yang";  

  prefix "auconyang";
  import simple-container-yang { prefix "simple"; revision-date 2013-11-12; }
  
  revision 2014-03-19 {    
  }

  augment "/simple:cont" {
    container cont3 {
        leaf lf31 {
            type string;
        }
    }
  }
   
}
