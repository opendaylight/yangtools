module ietf-netconf {
  namespace "urn:ietf:params:xml:ns:netconf:base:1.0";

  prefix nc;

  import ietf-yang-metadata {
    prefix md;
  }

  description
    "Fake module to define edit-config attribute 'operation' in terms
     of RFC7952. This module should not leak to the outside world and
     is used only internally by OpenDaylight.";

  revision 2011-06-01 {
    description
      "Initial revision;";
    reference
      "RFC 6241: Network Configuration Protocol";
  }

  md:annotation "operation" {
    description "Elements in the <config> subtree MAY contain an
                 \"operation\" attribute, which belongs to the NETCONF
                 namespace defined in Section 3.1.  The attribute
                 identifies the point in the configuration to perform
                 the operation and MAY appear on multiple elements
                 throughout the <config> subtree.

                 If the \"operation\" attribute is not specified, the
                 configuration is merged into the configuration
                 datastore.";
    reference
      "RFC 6241: Network Configuration Protocol";

    type enumeration {
      enum merge {
        description "The configuration data identified by the element
                     containing this attribute is merged with the
                     configuration at the corresponding level in the
                     configuration datastore identified by the <target>
                     parameter.  This is the default behavior.";
        reference
          "RFC 6241: Network Configuration Protocol";
      }

      enum replace {
        description "The configuration data identified by the element
                     containing this attribute replaces any related
                     configuration in the configuration datastore identified
                     by the <target> parameter.  If no such configuration
                     data exists in the configuration datastore, it is
                     created.  Unlike a <copy-config> operation, which
                     replaces the entire target configuration, only the
                     configuration actually present in the <config> parameter
                     is affected.";
        reference
          "RFC 6241: Network Configuration Protocol";
      }

      enum create {
        description "The configuration data identified by the element
                     containing this attribute is added to the configuration
                     if and only if the configuration data does not already
                     exist in the configuration datastore.  If the
                     configuration data exists, an <rpc-error> element is
                     returned with an <error-tag> value of \"data-exists\".";
        reference
          "RFC 6241: Network Configuration Protocol";
      }

      enum delete {
        description "The configuration data identified by the element
                     containing this attribute is deleted from the
                     configuration if and only if the configuration data
                     currently exists in the configuration datastore.  If the
                     configuration data does not exist, an <rpc-error>
                     element is returned with an <error-tag> value of
                     \"data-missing\".";
        reference
          "RFC 6241: Network Configuration Protocol";
      }

      enum remove {
        description "The configuration data identified by the element
                     containing this attribute is deleted from the
                     configuration if the configuration data currently exists
                     in the configuration datastore.  If the configuration
                     data does not exist, the \"remove\" operation is silently
                     ignored by the server.";
        reference
          "RFC 6241: Network Configuration Protocol";
      }
    }
  }
}
