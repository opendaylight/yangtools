module odl-test-identifier {
    yang-version 1;
    namespace "urn:opendaylight:params:xml:ns:yang:yangtools:test:identifier";
    prefix "oti";

    description
        "Testing allowed identifier names.";

    revision "2016-03-31" {
        description
            "Initial revision.";
    }

    grouping foo {
        leaf foo {
            type string;
        }
        leaf Foo {
            type string;
        }
        leaf foo0 {
            type string;
        }
        leaf foo_ {
            type string;
        }
        leaf foo- {
            type string;
        }
        leaf foo. {
            type string;
        }
    }

    container cont {
        uses foo;
    }

    container items {
        list item {
            key "foo Foo foo0 foo_ foo- foo."
            uses foo;
        }
    }

}
