module yt1442 {
  namespace yt1442;
  prefix yt1442;

  leaf foo {
    type decimal64 {
      fraction-digits 2;
      range 10.0..100.0 {
        error-app-tag model-defined-app-tag;
        error-message model-defined-message;
      }
    }
  }
}
