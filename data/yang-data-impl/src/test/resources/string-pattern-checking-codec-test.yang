module string-pattern-checking-codec-test {
    namespace "string-pattern-checking-codec-test";
    prefix "spcct";

    container test-container {
        leaf string-leaf-with-valid-pattern {
            type string {
                pattern "[A-Z]+";
            }
        }
    }
}
