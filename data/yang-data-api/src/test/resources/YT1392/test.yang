module test {
  namespace test;
  prefix test;

  container container-1 {
    container container-2 {
      container container-3 {
        container payload-container {
          leaf payload-leaf {
            type string;
          }
        }
      }
    }
  }

  choice choice-node {
    container container-in-case;
  }

  list list-1 {
    key list-1-key;

    leaf list-1-key {
      type string;
    }

    container container-1;
  }

  leaf-list list-list {
    type string;
  }
}
