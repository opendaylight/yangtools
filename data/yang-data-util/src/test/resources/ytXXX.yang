module foo {
  namespace foo;
  prefix foo;
  yang-version 1.1;

  container one {
    choice two {
      case three {
        leaf four {
          type string;
        }
      }
    }
  }

  augment /one {
    list five;
  }

  augment /one/two/three/three {
    leaf six {
      type string;
    }
  }
}
