/*
 * Copyright (c) 2013 Cisco Systems, Inc. and others.  All rights reserved.
 *
 * This program and the accompanying materials are made available under the
 * terms of the Eclipse Public License v1.0 which accompanies this distribution,
 * and is available at http://www.eclipse.org/legal/epl-v10.html
 */
module types1 {
    yang-version 1;
    namespace "urn:simple.container.demo.types1";
    prefix "t1";

    import types2 {
        prefix "data";
        revision-date 2013-02-27;
    }

   import types3 {
        prefix "t3";
        revision-date 2013-02-27;
    }

    organization "opendaylight";
    contact "http://www.opendaylight.org/";

    revision "2013-02-27" {
        reference " WILL BE DEFINED LATER";
    }

}
