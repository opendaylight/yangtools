module foo {
    namespace foo;
    prefix foo;

    import ietf-restconf {
        prefix rc;
    }

    revision 2017-06-01;

    rc:yang-data "my-yang-data" {
        // invalid top level node, it must be a container = should throw an exception
        leaf lf {
            type string;
        }
    }
}
