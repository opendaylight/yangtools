module baz {
    namespace baz;
    prefix baz;

    import ietf-restconf {
        prefix rc;
    }

    revision 2017-06-01;

    rc:yang-data "my-yang-data" {
        container cont {
            config false;

            container inner-cont {
                config false;
            }

            uses grp;
        }
    }

    grouping grp {
        container grp-cont {
            config false;
        }
    }
}
