module foo-tag-module {
  yang-version 1.1;
  namespace "https://example.com/yang/foo";
  prefix "ftm";

  import ietf-module-tags { prefix tags; }
  import ietf-module-tags-state { prefix tags-s; }

  revision "2022-04-05" {
    description "Initial version";
  }

  container cntr {
    tags:module-tag "ietf:tag-outside-cntr";
  }
}
