module ietf-module-tags-state {
     yang-version 1.1;
     namespace "urn:ietf:params:xml:ns:yang:ietf-module-tags-state";
     prefix tags-s;

     import ietf-yang-types {
       prefix yang;
     }

     import ietf-module-tags {
       prefix tags;
     }

     organization
       "IETF NetMod Working Group (NetMod)";
     contact
       "WG Web:  <https://datatracker.ietf.org/wg/netmod/>
        WG List: <mailto:netmod@ietf.org>

        Author: Christian Hopps
                <mailto:chopps@chopps.org>

        Author: Lou Berger
                <mailto:lberger@labn.net>

        Author: Dean Bogdanovic
                <mailto:ivandean@gmail.com>";

     description
       "This module describes a mechanism associating tags with YANG
        modules.  Tags may be IANA assigned or privately defined.

        This is a temporary non-NMDA module that is for use by
        implementations that don't yet support NMDA.

        Copyright (c) 2021 IETF Trust and the persons identified as
        authors of the code.  All rights reserved.

        Redistribution and use in source and binary forms, with or
        without modification, is permitted pursuant to, and subject to
        the license terms contained in, the Simplified BSD License set
        forth in Section 4.c of the IETF Trust's Legal Provisions
        Relating to IETF Documents
        (https://trustee.ietf.org/license-info).

        This version of this YANG module is part of RFC 8819
        (https://www.rfc-editor.org/info/rfc8819); see the RFC itself
        for full legal notices.";

     revision 2021-01-04 {
       description
         "Initial revision.";
       reference
         "RFC 8819: YANG Module Tags";
     }

     container module-tags-state {
       config false;
       status deprecated;
       description
         "Contains the list of modules and their associated tags.";
       list module {
         key "name";
         status deprecated;
         description
           "A list of modules and their associated tags.";
         leaf name {
           type yang:yang-identifier;
           mandatory true;
           status deprecated;
           description
             "The YANG module name.";
         }
         leaf-list tag {
           type tags:tag;
           status deprecated;
           description
             "Tags associated with the module.  See the IANA 'YANG
              Module Tag Prefixes' registry for reserved prefixes and
              the IANA 'IETF YANG Module Tags' registry for IETF tags.

              The contents of this list is constructed using the
              following steps:

              1) System tags (i.e., tags of added by the system) are
              added.
              2) User-configured tags (i.e., tags added by
              configuration) are added.
              3) Any tag that is equal to a masked-tag present in the
              corresponding ietf-module-tags:module-tags:module-tag leaf
              list for this module is removed.";
         }
       }
     }
   }
