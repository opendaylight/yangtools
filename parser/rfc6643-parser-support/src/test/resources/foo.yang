module foo {
    namespace "urn:opendaylight:yang:extension:third-party";
    prefix foo;
    yang-version 1;

    import ietf-yang-smiv2 { prefix "smiv2"; }

    revision 2016-06-09;

    typedef InterfaceIndexOrZero {
        type int32 {
            range "0..2147483647";
        }
        description
            "This textual convention is an extension of the
             InterfaceIndex convention.  The latter defines a greater
             than zero value used to identify an interface or interface
             sub-layer in the managed system.  This extension permits the
             additional value of zero.  the value zero is object-specific
             and must therefore be defined as part of the description of
             any object which uses this syntax.  Examples of the usage of
             zero might include situations where interface was unknown,
             or when none or all interfaces need to be referenced.";
        smiv2:display-hint "d";
    }

    container root {
        smiv2:oid "1";

        list ifStackEntry {
            smiv2:oid "1.1";
            smiv2:implied "ifStackHigherLayer";
            key "ifStackHigherLayer";

            leaf ifStackHigherLayer {
                type foo:InterfaceIndexOrZero;
                smiv2:max-access "not-accessible";
                description "The value of ifIndex corresponding to the higher sub-layer
                            of the relationship, i.e., the sub-layer which runs on 'top'
                            of the sub-layer identified by the corresponding instance of
                            ifStackLowerLayer.  If there is no higher sub-layer (below
                            the internetwork layer), then this object has the value 0.";
                smiv2:oid "1.1.1";
            }

            leaf test-number {
                type int32;
                description "Test leaf;";
                smiv2:max-access "not-accessible";
                smiv2:subid "2";
                smiv2:defval "0";
            }
        }
    }

    smiv2:alias "ifXTable" {
        description "A list of interface entries.  The number of entries is
                    given by the value of ifNumber.  This table contains
                    additional objects for the interface table.";
        smiv2:oid "1.3.6.1.2.1.31.1.1";
    }


}
