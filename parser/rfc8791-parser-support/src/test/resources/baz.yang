module baz {
  namespace baz;
  prefix baz;

  import ietf-yang-structure-ext { prefix sx; }
  import foo { prefix foo; }

  container cont {
    sx:structure boo-data {
      container boo-con {}
    }
    sx:augment-structure  /foo:foo-data/foo:foo-con {
      leaf add-leaf1 { type int32; }
      leaf add-leaf2 { type string; }
    }
  }
}
