module augment0 {
    yang-version 1;
    namespace "urn:simple.augment0.demo";
    prefix "a0";

    revision "2014-06-02";

    container foo {
        description "foo container";
        container bar {
            leaf id {
                type int8;
            }
            typedef int-ext {
                type int8 {
                    range "5..10";
                }
            }
            choice choice-ext {
                leaf delta {
                    type int8;
                }
            }
        }
    }

}
