module m1 {

    yang-version 1;
    namespace "urn:test.m1";
    prefix "m1";

    import m2 {
        prefix "m2";
        revision-date 2013-09-30;
    }
    import m3 {
        prefix "m3";
    }

    revision 2013-10-16 {
    }

}
