module foo {
    namespace "foo-namespace";
    prefix "foo-prefix";

    import foo-imp {
        prefix fimp;
        revision-date 2016-06-23;
    }

    revision "2016-06-23" {
        description "Initial revision";
    }

    deviation "/fimp:test-container/fimp:test-leaf" {
        description "test-leaf is not supported";
        deviate not-supported;
    }

    deviation "/fimp:test-container/fimp:test-leaf-2" {
        deviate add {
            default "added-def-val";
            config false;
            mandatory true;
        }
    }

    deviation "/fimp:test-container/fimp:test-leaf-list" {
        deviate add {
            max-elements 12;
        }

        deviate replace {
            min-elements 5;
            type uint32;
        }

        deviate delete {
            must "daytime or time";
            must "time or daytime";
            units minutes;
        }
    }

    deviation "/fimp:test-container/fimp:test-list" {
        deviate delete {
            unique "list-leaf-1 list-leaf-2";
            unique "list-leaf-3 list-leaf-4";
        }
    }
}
