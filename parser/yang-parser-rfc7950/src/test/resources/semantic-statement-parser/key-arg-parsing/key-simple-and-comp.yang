module key-simple-and-comp {
    namespace root;
    prefix root;

    list simple {
        key "key1";
        leaf key1 {
          type string;
        }
    }

    list comp {
        key "key1 key2 key3";
        leaf key1 {
          type string;
        }
        leaf key2 {
          type string;
        }
        leaf key3 {
          type string;
        }
    }
}
