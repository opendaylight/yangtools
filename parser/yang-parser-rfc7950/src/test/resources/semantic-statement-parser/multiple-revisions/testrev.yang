module testrev {
    yang-version 1;
    namespace "urn:tstrev:yang";
    prefix "tstrev";

    import importedrevtest { prefix "imprevtst"; }

    description "This is a test module";

    revision 2001-01-01 {
        description "initial version";
    }

    container mycontainer {
        leaf myleaf {
            type imprevtst:date-and-time;
        }
    }
}
