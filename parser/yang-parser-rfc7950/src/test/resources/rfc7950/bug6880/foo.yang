module foo {
    namespace "foo";
    prefix foo;
    yang-version 1.1;

    leaf-list my-leaf-list {
        type string;
        default "my-default-value-1";
        default "my-default-value-2";
    }
}
