module incorrect-list-keys-test5 {
    yang-version 1.1;
    namespace "incorrect-list-keys-test5";
    prefix "test";

    revision 2017-02-06 {
        description "Bug 6855: Test for uses stmt with refine substatement";
    }

    feature feature-a;

    grouping a {
        leaf a1 {
            type int32;
        }
    }

    list invalid-list-a1 {
        key a1;
        uses test:a {
            refine a1 {
                if-feature feature-a;
            }
        }
    }
}
