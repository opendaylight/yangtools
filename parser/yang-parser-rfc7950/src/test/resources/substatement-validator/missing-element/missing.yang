module missing {
    yang-version 1;
    namespace "urn:opendaylight.missing";
    prefix "missing";

    organization "opendaylight";
    contact "http://www.opendaylight.org/";

    revision "2015-11-11" {
        reference " WILL BE DEFINED LATER";
    }
}
