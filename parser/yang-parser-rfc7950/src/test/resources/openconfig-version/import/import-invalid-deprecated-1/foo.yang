module foo {
    namespace "foo";
    prefix foo;
    yang-version 1;

    import openconfig-extensions { prefix oc-ext; revision-date 2017-01-29; oc-ext:openconfig-version "1.0.0"; }

    revision "2016-02-01" {
        description "Initial version";
    }

    container root {
    }
}
