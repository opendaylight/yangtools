module foo {
    namespace foo;
    prefix foo;

    import bar {
        prefix bar;
        revision-date 2017-01-20;
    }

    revision 2017-01-20;

    deviation "/bar:my-leaf" {
        deviate add {
            config true;
        }
    }
}
