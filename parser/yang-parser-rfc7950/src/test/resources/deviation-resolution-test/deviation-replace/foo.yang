module foo {
    namespace foo;
    prefix foo;

    import bar {
        prefix bar;
    }

    revision 2017-01-20;

    deviation "/bar:my-leaf" {
        deviate replace {
            type uint32;
            default 10;
            units bytes;
        }
    }

    deviation "/bar:my-leaf-list-test" {
        deviate replace {
            min-elements 3;
            max-elements 6;
            config true;
        }
    }

    deviation "/bar:my-choice" {
        deviate replace {
            mandatory false;
            bar:custom-property "new arg";
        }
    }

    deviation "/bar:my-cont/bar:my-aug-leaf" {
        deviate replace {
            type uint32;
            default "new-def-val";
            units "seconds";
            bar:custom-property "new arg";
        }
    }

    deviation "/bar:my-cont/bar:my-used-leaf" {
        deviate replace {
            type uint32;
            default "new-def-val";
            bar:custom-property "new arg";
            units "weeks";
        }
    }
}
