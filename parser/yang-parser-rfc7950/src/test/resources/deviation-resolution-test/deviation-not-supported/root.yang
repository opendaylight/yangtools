module root {
    namespace root;
    prefix root;

    import imported {
        prefix imp;
        revision-date 2017-01-20;
    }

    revision 2017-01-20;

    deviation "/imp:my-cont-a/imp:my-leaf-a1" {
        deviate not-supported;
    }

    deviation "/imp:my-cont-a/imp:my-leaf-a2" {
        deviate not-supported;
    }

    deviation "/imp:my-cont-b" {
        deviate not-supported;
    }

    deviation "/imp:my-cont-c/imp:my-leaf-c3" {
        deviate not-supported;
    }
}
