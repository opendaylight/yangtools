module incorrect-list-keys-test {

    namespace "incorrect-list-keys-test";
    prefix "test";

    list test1 {
        key "test1_key1 test1_key2";
        leaf test1_key1 {
            type string;
        }
        list test1_key2 {
            leaf test1_key2 {
                type string;
            }
        }
    }
}
