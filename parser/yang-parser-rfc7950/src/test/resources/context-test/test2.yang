module test2 {

    yang-version 1;
    namespace "urn:simple.demo.test2";
    prefix "t2";

    import baz {
        prefix "data";
    }

    organization "opendaylight";
    contact "WILL-BE-DEFINED-LATER";
        revision 2013-06-18 {
    }

    container peer {
        container destination {
            uses data:target {
                refine address {
                    default "1.2.3.4";
                    description "description of address defined by refine";
                    reference "address reference added by refine";
                    config false;
                    mandatory true;
                    must "ifType != 'ethernet' or " +
                            "(ifType = 'ethernet' and ifMTU = 1500)" {
                        error-message "An ethernet MTU must be 1500";
                    }
                }
                refine port {
                    description "description of port defined by refine";
                    reference "port reference added by refine";
                    config false;
                    presence "presence is required";
                }
                refine addresses {
                    description "description of addresses defined by refine";
                    reference "addresses reference added by refine";
                    config false;
                    min-elements 2;
                    max-elements 12;
                }
            }
        }
    }

}
