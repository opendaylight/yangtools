module foo {
    yang-version 1;
    namespace "urn:opendaylight.foo";
    prefix "foo";

    import bar {
        prefix "br";
        revision-date 2013-10-14;
    }

    import baz {
        prefix "bz";
        revision-date 2013-10-15;
    }

    organization "opendaylight";
    contact "http://www.opendaylight.org/";

    revision "2013-10-13" {
        reference " WILL BE DEFINED LATER";
    }


    augment "/br:interfaces/br:ifEntry/bz:augment-holder" {
        when "br:ifType='ds0'";
        leaf ds0ChannelNumber {
            type string;
        }
        leaf interface-id {
            type leafref {
                path "/br:interfaces/br:ifEntry/br:ifIndex";
            }
        }
        container schemas {
        }
        choice odl {
            leaf id {
                type int8;
            }
            case node1 {
                description "node1";
            }
            case node2 {
                description "node2";
            }
            container node3 {
                description "node3";
            }
        }
    }


    uses bz:target {
        augment "how/interval" {
            description "inner augment";
            leaf name {
                type string;
            }
        }
    }

}
