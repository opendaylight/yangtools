module root-module {
    namespace "root-module";
    prefix root;

    import imported-module { prefix imp; }
    
    include submodule-1;
    include submodule-2;

    container container-in-root-module {
        description "desc";
    }
}
