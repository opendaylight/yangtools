module foo {
    namespace foo-namespace;
    prefix foo-prefix;

    revision 2016-09-23;

    rpc foo-rpc-1 {
        input {
            leaf foo-leaf-1 {
                type string;
            }
        }

        output {
            leaf foo-leaf-2 {
                type string;
            }
        }
    }

    rpc foo-rpc-2 {
        input {
            leaf foo-leaf-3 {
                type string;
            }
        }

        output {
            leaf foo-leaf-4 {
                type string;
            }
        }
    }
}
