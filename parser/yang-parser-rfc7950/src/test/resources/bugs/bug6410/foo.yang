module foo {
    namespace foo-namespace;
    prefix foo-prefix;

    revision 2016-08-16;

    rpc test-rpc {
        typedef test-string-typedef {
            type string {
                length "5..15";
            }
            default "def-val";
        }
        typedef test-int-typedef {
            type int32 {
                range "10..100";
            }
            default 50;
        }
    }
}
