module qux {
  yang-version 1.1;
  namespace qux;
  prefix qux;

  import foo { prefix foo; }

  augment /foo:cfg {
    leaf bar {
      type string;
      mandatory true;
      config false;
    }
  }
}
