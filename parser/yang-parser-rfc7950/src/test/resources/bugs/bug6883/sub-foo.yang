submodule sub-foo {
    yang-version 1.1;

    belongs-to foo {
        prefix foo;
    }

    anydata sub-data {
        description "submodule anydata";
        status current;
        mandatory true;
        must "1!=0";
    }
}
