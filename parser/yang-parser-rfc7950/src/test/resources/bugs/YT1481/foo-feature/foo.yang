module foo {
  namespace "urn:foo";
  prefix "foo";

  feature foo-feature;

  container foo {
    if-feature foo-feature;

    list bar {
      key baz;
      unique qux;

      leaf baz {
        type string;
      }

      leaf qux {
        type string;
      }
    }
  }
}
