submodule baz {
  belongs-to foo {
    prefix foo;
  }

  augment "/foo:bar" {
    container plan-notifications {
      list subscription {
        key name;
        unique "service-type component-type";
        leaf name {
          type string;
        }
        leaf service-type {
          type string;
        }
        leaf component-type {
          type string;
        }
      }
    }
  }
}
