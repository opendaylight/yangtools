submodule test-bug {
  yang-version 1.1;
  belongs-to main-module {
    prefix mm;
  }

  augment "/mm:services" {
    container plan-notifications {
      list subscription {
        key name;
        unique "service-type component-type";
        leaf name {
          type string;
        }
        leaf service-type {
          type string;
        }
        leaf component-type {
          type string;
        }
      }
    }
  }
}
