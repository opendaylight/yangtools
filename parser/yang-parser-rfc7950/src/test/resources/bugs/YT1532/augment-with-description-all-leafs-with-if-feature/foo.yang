module foo {
  namespace "urn:foo";
  prefix "foo";

  feature alpha;

  grouping foo-group {
    container foo;
  }

  grouping bar-group {
    uses foo-group {
      augment foo {
        description "augmentation to foo";
        leaf bar1 {
          if-feature alpha;
          type string;
        }
        leaf bar2 {
          if-feature alpha;
          type string;
        }
      }
    }
  }

  uses bar-group {
    augment foo {
      leaf baz {
        type string;
      }
    }
  }
}
