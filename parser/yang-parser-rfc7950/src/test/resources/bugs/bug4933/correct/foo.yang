module foo {
    yang-version 1;
    namespace "foo";
    prefix foo;

    import bar {
        prefix bar;
    }

    deviation /bar:my-container/bar:my-leaf-list {
        deviate add {
            min-elements 1;
        }
    }

    deviation /bar:my-container/bar:my-leaf-list {
        deviate replace {
            max-elements 10;
        }
    }

    deviation /bar:my-container/bar:my-leaf-list {
        deviate delete {
            must "0 != 1";
        }
    }

    deviation /bar:my-container2 {
        deviate not-supported;
    }
}
