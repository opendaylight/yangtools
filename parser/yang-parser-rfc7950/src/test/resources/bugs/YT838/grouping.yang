module grouping {
    namespace grouping;
    prefix grp;

    revision "2017-12-20";

    container top {
        grouping foo {

        }

        container nested {
            grouping foo {

            }
        }
    }
}
