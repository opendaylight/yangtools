module bar {
     namespace bar-ns;
     prefix bar-prefix;

     import foo {
         prefix foo;
         revision-date 2016-10-20;
     }

     revision 2016-10-20;

     container bar-export {
         uses foo:export;
     }
     container bar-foo {
         uses foo:foo;
     }
}
