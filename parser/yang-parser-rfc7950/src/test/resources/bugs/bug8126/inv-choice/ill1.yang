module ill1 {
    namespace ill1;
    prefix ill1;

    import foo { prefix foo; }

    //invalid augment (mandatory choice)
    augment "/foo:root" {
        container mandatory-container {
            choice mandatory-choice {
                mandatory true;
            }
        }
    }
}
