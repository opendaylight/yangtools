module foo {
    namespace "foo";
    prefix foo;
    yang-version 1;

    revision "2016-03-04" {
        description "test";
    }

    container root {
    }

    augment "/root" {
        container non-presence-container {
        }
    }

    augment "/root/non-presence-container" {
        leaf mandatory-leaf {
            type string;
            mandatory true;
        }
    }
}
