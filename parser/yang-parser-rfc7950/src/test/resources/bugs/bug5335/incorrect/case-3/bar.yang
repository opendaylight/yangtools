module bar {
    namespace "bar";
    prefix bar;
    yang-version 1;

    import foo { prefix foo; revision-date 2016-03-04; }

    revision "2016-03-04" {
        description "test";
    }

    augment "/foo:root/foo:presence-container" {
        container non-presence-container {
        }
    }

    include sub-bar;
}
