module foo {
    namespace foo;
    prefix foo;
    yang-version 1.1;

    container root {
        leaf my-leafref {
            type leafref {
                path "../target";
                require-instance false;
            }
        }
        leaf target {
            type string;
        }
    }
}
