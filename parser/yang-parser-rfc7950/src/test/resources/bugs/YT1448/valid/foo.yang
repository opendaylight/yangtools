module foo {
  yang-version 1.1;
  namespace "urn:test:foo";
  prefix foo;

  include foo-submodule;

  revision 2022-02-22;

  container object {
    list items {
      key "name";
      leaf name {
        type string;
      }
    }
  }

}
