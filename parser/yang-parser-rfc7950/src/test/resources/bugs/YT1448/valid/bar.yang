module bar {
  yang-version 1.1;
  namespace "urn:test:bar";
  prefix bar;

  revision 2022-02-22;

  container object {
    list items {
      key "name";
      leaf name {
        type string;
      }
      leaf str {
        type string;
      }
      leaf boolean {
        type boolean;
      }
    }
  }
}
