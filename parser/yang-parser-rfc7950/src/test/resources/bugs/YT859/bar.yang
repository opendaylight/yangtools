module bar {
  yang-version 1.1;
  namespace bar;
  prefix bar;

  import xyzzy { prefix xyzzy; }
  import foo { prefix foo; }

  augment /xyzzy:xyzzy/xyzzy:named/foo:foo {
    container bar;
  }

  deviation /xyzzy:xyzzy/xyzzy:named/foo:foo {
    deviate add {
      config false;
    } 
  }
}
