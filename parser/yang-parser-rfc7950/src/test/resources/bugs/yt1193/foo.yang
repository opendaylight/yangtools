module foo {
  namespace foo;
  prefix foo;
  yang-version 1.1;

  revision 2021-04-26;

  organization org;
  description desc;
  reference ref;
  contact cont;

  container foo {
    action act {
      input {

      }
      output {

      }
    }
    presence presence;
  }

  rpc rpc;
  notification notif;

  leaf-list depr {
    type string {
      length 1 {
        error-app-tag tag;
        error-message msg;
      }
    }

    units dinosaurs;
    status deprecated;
  }

  typedef obso {
    type leafref {
      path /foo:depr;
    }
    status obsolete;
  }
}
