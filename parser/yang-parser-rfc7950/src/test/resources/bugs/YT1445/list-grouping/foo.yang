module foo {
  namespace "urn:foo";
  prefix "foo";

  grouping bar-group {
    list bar {
      key bar;
      unique baz;

      leaf bar {
        type string;
      }

      leaf baz {
        type string;
      }
    }
  }

  container foo {
    uses bar-group;
  }
}
