module leafref-absolute-invalid {
    namespace "urn:xml:ns:yang:lra";
    prefix lra;
    revision "2015-02-25";

    list neighbor {
        description
           "List of neighbors.";
        leaf neighbor-id {
            type leafref {
                path "/lra:neighbor/lra:neighbor-id";
            }
            description "Neighbor.";
        }
    }
}
