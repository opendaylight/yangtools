module base-yang-types {
    yang-version 1;
    namespace "urn:opendaylight:org:test:base:yang:types";
    prefix "tp";

    organization "OPEN DAYLIGHT";
    contact "http://www.opendaylight.org/";

    description "This module contains definitions of all Yang base types.";

    revision "2014-09-14" {
        reference "Added yang-int8-restricted type.";
     }

    revision "2014-07-23" {
        reference "Initial Revision.";
    }

    typedef yang-boolean {
        type boolean;
    }

    typedef yang-empty {
        type empty;
    }

    typedef yang-enumeration {
        type enumeration {
            enum a;
            enum b;
        }
    }

    typedef yang-int8 {
        type int8;
    }

    typedef yang-int8-restricted {
        type int8 {
            range 1..100;
        }
    }

    typedef yang-int16 {
        type int16;
    }

    typedef yang-int32 {
        type int32;
    }

    typedef yang-int64 {
        type int64;
    }

    typedef yang-string {
        type string;
    }

    typedef yang-decimal64 {
        type decimal64 {
            fraction-digits 2;
        }
    }

    typedef yang-uint8 {
        type uint8;
    }

    typedef yang-uint16 {
        type uint16;
    }

    typedef yang-uint32 {
        type uint32;
    }

    typedef yang-uint64 {
        type uint64;
    }

    typedef yang-union {
        type union {
            type int32;
            type int16;
        }
    }

    typedef yang-binary {
        type binary;
    }

    typedef yang-bits {
        type bits {
            bit disable-nagle {
                position 0;
            }
            bit auto-sense-speed {
                position 1;
            }
            bit 10-Mb-only {
                position 2;
            }
        }
        default "auto-sense-speed";
    }

    typedef yang-instance-identifier {
        type instance-identifier;
    }
}
