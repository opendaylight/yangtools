module opendaylight-yangtools-augment-test {

    namespace "urn:opendaylight:params:xml:ns:yang:yangtools:test:augment";
    prefix aug-test;

    import opendaylight-yangtools-binding-test {
        prefix test;
    }
    import yang-ext {
        prefix ext;
    }

    description
        "This module contains a collection of YANG augmentations used for
        some test cases.";

    revision 2014-07-09 {
        description
        "Test model for testing data broker with nested lists.";
    }

    identity third-party {
        base test:test-root;
    }

    grouping leaf-from-grouping {
        leaf leaf-from-grouping {
            type string;
        }
    }

    grouping complex-from-grouping {
        container container-with-uses {
            uses leaf-from-grouping;
        }
        list list-via-uses {
            key "name";
            leaf name {
                type string;
            }
        }
    }

    augment "/test:top/test:top-level-list" {
        ext:augment-identifier tree-leaf-only-uses-augment;
        uses leaf-from-grouping;
    }

    augment "/test:top/test:top-level-list" {
        ext:augment-identifier tree-complex-leaves;
        leaf simple-type {
            type int32;
        }
        leaf identity {
            type test:test-identityref;
        }
        leaf schema-unaware-union {
            type test:int32-string-union;
        }

        leaf simple-type-ref {
            type leafref {
                path "../simple-type";
            }
        }
        leaf identity-ref {
            type leafref {
                path "../identity";
            }
        }
        leaf schema-unaware-union-ref {
            type leafref {
                path "../schema-unaware-union";
            }
        }
    }


    augment "/test:put-top/test:input/test:top-level-list" {
        ext:augment-identifier rpc-leaf-only-uses-augment;
        uses leaf-from-grouping;
    }

    augment "/test:top/test:top-level-list" {
        ext:augment-identifier tree-complex-uses-augment;
        uses complex-from-grouping;
    }

    augment "/test:put-top/test:input/test:top-level-list" {
        ext:augment-identifier rpc-complex-uses-augment;
        uses complex-from-grouping;
    }

    augment "/test:top/test:top-level-list" {
        ext:augment-identifier tree-leaf-only-augment;

        leaf simple-value {
            type string;
        }
    }

    augment "/test:top/test:top-level-list" {
        ext:augment-identifier tree-second-leaf-only-augment;

        leaf second-simple-value {
            type string;
        }
    }

    augment "/test:put-top/test:input/test:top-level-list" {
        ext:augment-identifier rpc-leaf-only-augment;

        leaf simple-value {
            type string;
        }
    }

    augment "/test:put-top/test:input/test:top-level-list" {
        ext:augment-identifier rpc-second-leaf-only-augment;

        leaf second-simple-value {
            type string;
        }
    }

    augment "/test:top/test:top-level-list/test:choice-in-list" {
        case simple-via-uses {
            uses leaf-from-grouping;
        }
        case complex-via-uses {
            uses complex-from-grouping;
        }
        case empty-leaf {
            leaf empty-type {
                type empty;
            }
        }
    }

    augment "/test:put-top/test:input/test:top-level-list/test:choice-in-list" {
        case simple-via-uses {
            uses leaf-from-grouping;
        }
        case complex-via-uses-with-different-name {
            uses complex-from-grouping;
        }
    }

    augment "/test:top" {
        ext:augment-identifier top-choice-augment1;
        choice augment-choice1 {
            case case1 {
                container case1-container {
                    leaf case1-leaf {
                        type string;
                    }
                }
            }

            case case2 {
                container case2-container {
                    leaf case2-leaf {
                        type string;
                    }
                }
            }
        }
    }

    augment "/test:top/augment-choice1/case1" {
        ext:augment-identifier top-choice-augment2;
        choice augment-choice2 {
            case case11 {
                container case11-choice-case-container {
                    leaf case11-choice-case-leaf {
                        type string;
                    }
                }
            }
        }
    }

}
