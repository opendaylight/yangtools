module foo {
    yang-version 1;
    namespace "urn:opendaylight:foo";
    prefix "f";
    
    import bar { prefix "b"; }

    revision "2013-10-08" {
    }

    extension context-reference {
    }

    container nodes {
        leaf id {
            type instance-identifier;
            context-reference "b:identity-class";
        }
        leaf-list constraints {
            type string;
        }
    }

}
