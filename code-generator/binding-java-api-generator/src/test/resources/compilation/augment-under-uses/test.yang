module test {
    yang-version 1;
    namespace "urn:opendaylight:test";
    prefix "t";

    revision "2013-10-08" {
    }

    grouping object {
        container nodes {
        }
    }

    grouping open-object {
        uses object {
            augment "nodes" {
                container links {
                    leaf id {
                        type string;
                    }
                }
            }
        }
    }

}
