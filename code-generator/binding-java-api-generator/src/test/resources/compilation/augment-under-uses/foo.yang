/*
 * Copyright (c) 2013 Cisco Systems, Inc. and others.  All rights reserved.
 *
 * This program and the accompanying materials are made available under the
 * terms of the Eclipse Public License v1.0 which accompanies this distribution,
 * and is available at http://www.eclipse.org/legal/epl-v10.html
 */
module foo {
    yang-version 1;
    namespace "urn:opendaylight:foo";
    prefix "foo";

    import bar { prefix b; revision-date 2013-10-08; }

    revision "2013-10-08" {
    }

    grouping object {
        container nodes {
        }
    }

    grouping open-object {
        uses object {
            augment "nodes" {
                container links {
                    leaf id {
                        type string;
                    }
                }
            }
        }
    }

    grouping closed-object {
        uses b:route-subobjects {
            augment "links/link" {
                leaf id {
                    type string;
                }
            }
        }
    }

    grouping explicit-route-object {
        list subobjects {
            leaf loose {
                type boolean;
            }
            uses b:explicit-route-subobjects {
                augment "subobject-type" {
                    case path-key {
                        container path-key {
                            uses path-key-subobject;
                        }
                    }
                }
            }
        }
    }

    grouping path-key-subobject {
        leaf path-key {
            type string;
        }
    }

}
