/*
 * Copyright (c) 2013 Cisco Systems, Inc. and others.  All rights reserved.
 *
 * This program and the accompanying materials are made available under the
 * terms of the Eclipse Public License v1.0 which accompanies this distribution,
 * and is available at http://www.eclipse.org/legal/epl-v10.html
 */
module test {
    yang-version 1;
    namespace "urn:opendaylight:test";
    prefix "t";

    revision "2013-10-08" {
    }

    container foo {
        grouping bar {
            leaf id {
                type int32;
            }
        }
        uses bar;
    }

}
