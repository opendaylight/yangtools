/*
 * Copyright (c) 2013 Cisco Systems, Inc. and others.  All rights reserved.
 *
 * This program and the accompanying materials are made available under the
 * terms of the Eclipse Public License v1.0 which accompanies this distribution,
 * and is available at http://www.eclipse.org/legal/epl-v10.html
 */
module testDoc3 {
    yang-version 1;
    namespace "urn:opendaylight.testDoc3";
    prefix "testDoc3";

    import testDoc1 {
        prefix "testDoc1";
        revision-date 2013-10-08;
    }
	
	description "TestDoc3 - Network topology is the arrangement of the various elements (links, nodes, etc.) of a computer network.[1][2] Essentially, it is the topological[3] structure of a network, and may be depicted physically or logically. Physical topology is the placement of the various components of a network, including device location and cable installation, while logical topology illustrates how data flows within a network, regardless of its physical design. Distances between nodes, physical interconnections, transmission rates, or signal types may differ between two networks, yet their topologies may be identical.";
	reference "RFC 6020 - http://tools.ietf.org/html/rfc6020";

    revision "2013-10-08" {
    }


    augment "/testDoc1:network-topology/testDoc1:topology/testDoc1:link" {
        uses igp-link-attributes;
    }

    grouping igp-link-attributes {
        container igp-link-attributes {
			description "Igp-link-attributes - Network topology is the arrangement of the various elements (links, nodes, etc.) of a computer network.[1][2] Essentially, it is the topological[3] structure of a network, and may be depicted physically or logically. Physical topology is the placement of the various components of a network, including device location and cable installation, while logical topology illustrates how data flows within a network, regardless of its physical design. Distances between nodes, physical interconnections, transmission rates, or signal types may differ between two networks, yet their topologies may be identical.";
			reference "RFC 6020 - http://tools.ietf.org/html/rfc6020";
		
            leaf name {
				description "Name - Network topology is the arrangement of the various elements (links, nodes, etc.) of a computer network.[1][2] Essentially, it is the topological[3] structure of a network, and may be depicted physically or logically. Physical topology is the placement of the various components of a network, including device location and cable installation, while logical topology illustrates how data flows within a network, regardless of its physical design. Distances between nodes, physical interconnections, transmission rates, or signal types may differ between two networks, yet their topologies may be identical.";
				reference "RFC 6020 - http://tools.ietf.org/html/rfc6020";
                type string;
            }
            leaf-list flag {
				description "Flag - Network topology is the arrangement of the various elements (links, nodes, etc.) of a computer network.[1][2] Essentially, it is the topological[3] structure of a network, and may be depicted physically or logically. Physical topology is the placement of the various components of a network, including device location and cable installation, while logical topology illustrates how data flows within a network, regardless of its physical design. Distances between nodes, physical interconnections, transmission rates, or signal types may differ between two networks, yet their topologies may be identical.";
				reference "RFC 6020 - http://tools.ietf.org/html/rfc6020";
                type string;
            }
            leaf metric {
				description "Metric - Network topology is the arrangement of the various elements (links, nodes, etc.) of a computer network.[1][2] Essentially, it is the topological[3] structure of a network, and may be depicted physically or logically. Physical topology is the placement of the various components of a network, including device location and cable installation, while logical topology illustrates how data flows within a network, regardless of its physical design. Distances between nodes, physical interconnections, transmission rates, or signal types may differ between two networks, yet their topologies may be identical.";
				reference "RFC 6020 - http://tools.ietf.org/html/rfc6020";
                type uint32 {
                    range "0..16777215"  {
                    }
                }
            }
        }
    }

}
