module bar {
    yang-version 1;
    namespace "urn:opendaylight:bar";
    prefix "bar";

    import baz { prefix bz; revision-date 2013-10-08; }

    revision "2013-10-08" {
    }

    grouping bar_gr1 {
        leaf bar1 {
            type int8;
        }
        leaf bar2 {
            type int16;
        }
    }

    grouping bar_gr2 {
        leaf bar3 {
            type int32;
        }
        uses bar_gr1;
        uses bz:baz_gr1;
    }

}
