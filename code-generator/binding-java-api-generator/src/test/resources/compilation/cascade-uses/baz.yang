/*
 * Copyright (c) 2013 Cisco Systems, Inc. and others.  All rights reserved.
 *
 * This program and the accompanying materials are made available under the
 * terms of the Eclipse Public License v1.0 which accompanies this distribution,
 * and is available at http://www.eclipse.org/legal/epl-v10.html
 */
module baz {
    yang-version 1;
    namespace "urn:opendaylight:baz";
    prefix "baz";

    revision "2013-10-08" {
    }

    grouping baz_gr1 {
        leaf baz1 {
            type uint8;
        }
    }

}
