/*
 * Copyright (c) 2013 Cisco Systems, Inc. and others.  All rights reserved.
 *
 * This program and the accompanying materials are made available under the
 * terms of the Eclipse Public License v1.0 which accompanies this distribution,
 * and is available at http://www.eclipse.org/legal/epl-v10.html
 */
module simple-list-demo {
	yang-version 1;
    namespace "urn:simple.container.demo";
    prefix "scd";

    organization "OPEN DAYLIGHT";
    contact "http://www.opendaylight.org/";

    description "
        This module contains the definitions of elements that creates network 
        topology i.e. definition of network nodes and links. This module is
        not designed to be used solely for network representation. This module
        SHOULD be used as base module in defining the network topology.
    ";

    revision "2013-02-27" {
        reference " WILL BE DEFINED LATER";
    }

    container list-parent-container {

    	list simple-list {
    		key "list-key";

    		leaf list-key {
    			type int8;
    		}
            
            container list-child-container {
                leaf foo {
                    type uint8;
                }
            }
            
    		leaf foo {
    			type int32;
    		}
            
            leaf-list simple-leaf-list {
                type int32;
            }
            
    		leaf bar {
    			type string;
    			config true;
    		}	
    	}
    }
}
