//
// Copyright (c) 2013 Cisco Systems, Inc. and others.  All rights reserved.
//
// This program and the accompanying materials are made available under the
// terms of the Eclipse Public License v1.0 which accompanies this distribution,
// and is available at http://www.eclipse.org/legal/epl-v10.html
//
module controller-openflow-ipv6 {
	yang-version 1;
	namespace "urn:opendaylight:controller:network:openflow:ipv6";
	prefix "of6";

	import controller-network {
		prefix cn;
	}
	import ietf-inet-types { prefix "inet"; }
	import controller-openflow-ne {prefix "of";}

	revision 2013-06-07 {
	   description "Initial demo";
	}
}
