//
// Copyright (c) 2013 Cisco Systems, Inc. and others.  All rights reserved.
//
// This program and the accompanying materials are made available under the
// terms of the Eclipse Public License v1.0 which accompanies this distribution,
// and is available at http://www.eclipse.org/legal/epl-v10.html
//
module simple-string-demo {

    namespace "urn:simple:string:demo";
    prefix "sbd";

    organization "OPEN DAYLIGHT";
    contact "http://www.opendaylight.org/";

    revision 2013-06-18 {
        
    }

    typedef typedef-string {
        type string {
            length "40";
            pattern "[0-9A-F]\.*";
            pattern "[B-D]*";
            pattern "[4-7]*";
        }
    }

}
