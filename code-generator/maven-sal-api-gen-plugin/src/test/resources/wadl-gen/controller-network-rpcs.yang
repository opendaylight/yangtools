/*
 * Copyright (c) 2013 Cisco Systems, Inc. and others.  All rights reserved.
 *
 * This program and the accompanying materials are made available under the
 * terms of the Eclipse Public License v1.0 which accompanies this distribution,
 * and is available at http://www.eclipse.org/legal/epl-v10.html
 */
module controller-network-rpcs {
	yang-version 1;
	namespace "urn:opendaylight:controller:network:rpcs";
	prefix "topos";
	
	import ietf-inet-types { prefix "inet"; }
	
	revision 2013-05-20 {
	   description "Initial demo";
	}
	
	rpc activate-software-image {
         input {
             leaf image-name {
                 type string;
             }
         }
         output {
             leaf status {
                 type string;
             }
         }
     }
     
     rpc rock-the-house {
         input {
             leaf zip-code {
                 type string;
             }
         }
     }
}
