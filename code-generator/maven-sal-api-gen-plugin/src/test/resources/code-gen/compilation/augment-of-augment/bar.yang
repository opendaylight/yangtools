/*
 * Copyright (c) 2013 Cisco Systems, Inc. and others.  All rights reserved.
 *
 * This program and the accompanying materials are made available under the
 * terms of the Eclipse Public License v1.0 which accompanies this distribution,
 * and is available at http://www.eclipse.org/legal/epl-v10.html
 */
module bar {
    yang-version 1;
    namespace "urn:opendaylight:bar";
    prefix "bar";

    import foo { prefix fo; revision-date 2013-10-08; }

    revision "2013-10-08" {
    }

    augment "/fo:update/fo:path-attributes" {
        container mp-unreach-nlri {
            container withdrawn-routes {
                uses destination;
            }
        }
    }

    grouping destination {
        choice destination-type {
            case destination-ip {
                leaf-list prefixes {
                    type string;
                }
            }
        }
    }

}
