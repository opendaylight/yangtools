/*
 * Copyright (c) 2013 Cisco Systems, Inc. and others.  All rights reserved.
 *
 * This program and the accompanying materials are made available under the
 * terms of the Eclipse Public License v1.0 which accompanies this distribution,
 * and is available at http://www.eclipse.org/legal/epl-v10.html
 */
module bar {
    yang-version 1;
    namespace "urn:opendaylight.bar";
    prefix "bar";

    revision "2013-10-08" {
    }

    container network-topology {
        list topology {
            key "topology-id";
            leaf topology-id {
                type int32;
            }
            uses link;
        }
    }

    grouping link {
        list link {
            key "link-id";
            uses link-attributes;
        }
    }

    grouping link-attributes {
        leaf link-id {
            type int8;
        }
    }

}
