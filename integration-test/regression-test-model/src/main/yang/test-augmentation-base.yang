module test-augmentation-base {
    yang-version 1;
    namespace "urn:opendaylight:yang:test:regression:augmentation:base";
    prefix "aug-base";
    
    contact "Anton Tkacik <ttkacik@cisco.com>";

    description 
            "Copyright (c) 2014 Cisco Systems, Inc. and others.  All rights reserved.

            This program and the accompanying materials are made available under the
            terms of the Eclipse Public License v1.0 which accompanies this distribution,
            and is available at http://www.eclipse.org/legal/epl-v10.html";

    revision "2014-04-24" {
        description "";
    }

    grouping grouping {
        container grouping-data {

        }
    }
    
    grouping augmented-grouping {
        uses grouping {
            augment grouping-data {
                leaf augmented-leaf {
                    type string;
                }
            }
        }
    }


    container choices {
        description "
            Empty Container which could be used by augmentation tests.
            This container is used for regression tests of Bug 466.
            ";
        choice augmentable-choice {
            case not-augmented {
                container not-augmented {
                    uses grouping;
                }
            }
            case with-augmented-grouping {
                container with-augmented-grouping {
                    uses augmented-grouping;
                }
            }
        }
    }
}
