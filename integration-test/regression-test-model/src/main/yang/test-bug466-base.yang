module test-bug466-base {
    yang-version 1;
    namespace "urn:opendaylight:yang:test:regression:bug466:base";
    prefix "bug466-base";
    
    contact "Anton Tkacik <ttkacik@cisco.com>";

    description 
            "Copyright (c) 2014 Cisco Systems, Inc. and others.  All rights reserved.

            This program and the accompanying materials are made available under the
            terms of the Eclipse Public License v1.0 which accompanies this distribution,
            and is available at http://www.eclipse.org/legal/epl-v10.html";

    revision "2014-02-26" {
        description "";
    }
    
    identity bug-466-identity {
        description "Testing identity.";
    }

    container bug-466 {
        description "
            Empty Container which could be used by augmentation tests.
            This container is used for regression tests of Bug 466.
            ";
        leaf condition {
            type string;
        }
    }
}
