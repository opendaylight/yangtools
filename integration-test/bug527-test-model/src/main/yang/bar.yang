/*
 * Copyright (c) 2013 Cisco Systems, Inc. and others.  All rights reserved.
 *
 * This program and the accompanying materials are made available under the
 * terms of the Eclipse Public License v1.0 which accompanies this distribution,
 * and is available at http://www.eclipse.org/legal/epl-v10.html
 */
module bar {
    yang-version 1;
    namespace "urn:yang:bar";
    prefix "bar";

    import baz {
        prefix "baz";
    }

    revision "2014-03-21" {
    }

    container factory {
        container alpha {
            uses baz:machine-def;
        }
        container beta {
            uses baz:machine-def;
        }
    }
    
    rpc create-factory {
        input {
            uses baz:machine-def;
        }
    }
    
    rpc create-nested-factory {
        input {
            container nested {
                uses baz:machine-def;
            }
        }
    }

    grouping machine-types {
        container types {
            choice machine-type {
            }
        }
    }

    grouping machine-ext {
        uses machine-types {
            augment "types/machine-type" {
                case type-a {
                    leaf id {
                        type string;
                    }
                }
            }
        }
    }

}
