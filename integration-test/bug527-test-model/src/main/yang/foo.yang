/*
 * Copyright (c) 2013 Cisco Systems, Inc. and others.  All rights reserved.
 *
 * This program and the accompanying materials are made available under the
 * terms of the Eclipse Public License v1.0 which accompanies this distribution,
 * and is available at http://www.eclipse.org/legal/epl-v10.html
 */
module foo {
    yang-version 1;
    namespace "urn:yang:foo";
    prefix "foo";

    import bar {
        prefix bar;
    }
    
    import yang-ext {
        prefix ext;
    }

    revision "2014-03-21" {
    }

    augment "/bar:factory/bar:alpha/bar:machine/bar:atts" {
        description "Alpha Augmentation";
        ext:augment-identifier alpha-ext;
        uses bar:machine-ext;
    }

    augment "/bar:factory/bar:beta/bar:machine/bar:atts" {
        description "Beta Augmentation";
        ext:augment-identifier beta-ext;
        uses bar:machine-ext;
    }

    augment "/bar:create-factory/bar:input/bar:machine/bar:atts" {
        description "Create Factory Augmentation";
        ext:augment-identifier create-ext;
        uses bar:machine-ext;
    }

    augment "/bar:create-nested-factory/bar:input/bar:nested/bar:machine/bar:atts" {
        description "Create Nested Augmentation";
        ext:augment-identifier create-nested-ext;
        uses bar:machine-ext;
    }
}
