module test-module {

	yang-version 1;
    namespace "urn:opendaylight:params:xml:ns:yangtools:restconf";
    prefix "remote-test";


    organization "Cisco Systems, Inc.";
    contact "Martin Bobak <mbobak@cisco.com>";

    description
          "This is just test module for restconf-client-impl testing.

           Copyright (c)2013 Cisco Systems, Inc. All rights reserved.

           This program and the accompanying materials are made available
           under the terms of the Eclipse Public License v1.0 which
           accompanies this distribution, and is available at
           http://www.eclipse.org/legal/epl-v10.html";

    revision "2014-01-14" {
        description
            "Initial revision";
    }


    rpc test-methodA {
        input {
            leaf string-value {
                type string;
            }
         }
         output {
            leaf string-value{
                type string;
            }
         }
    }

}
