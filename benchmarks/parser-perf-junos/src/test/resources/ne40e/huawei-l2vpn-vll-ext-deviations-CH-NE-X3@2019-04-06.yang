/*
Copyright (C) 2019 Huawei Technologies Co., Ltd. All rights reserved.
*/
module huawei-l2vpn-vll-ext-deviations-CH-NE-X3 {
  namespace "urn:huawei:yang:huawei-l2vpn-vll-ext-deviations-CH-NE-X3";
  prefix "l2vpn-vll-ext-devs-CH-NE-X3";

  import huawei-ifm {
    prefix "ifm";
  }
  import huawei-l2vpn-vll-ext {
    prefix "l2vpn-vll-ext";
  }

  organization
    "Huawei Technologies Co., Ltd.";
  contact
    "Huawei Industrial Base
     Bantian, Longgang
     Shenzhen 518129
     People's Republic of China
     Website: http://www.huawei.com
     Email: support@huawei.com";
  description
    "L2VPN vll ext.";
  revision 2019-04-06 {
    description
      "The modifications in the schema file are synchronized to the YANG file.";
    reference
      "Huawei private.";
  }
  
  deviation /ifm:ifm/ifm:interfaces/ifm:interface/l2vpn-vll-ext:vll-pw-loop-check {
    deviate not-supported;
  }
}
