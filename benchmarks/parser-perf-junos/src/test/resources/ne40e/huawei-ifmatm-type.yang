/*
Copyright (C) 2013-2017 Huawei Technologies Co., Ltd. All rights reserved.
*/
submodule huawei-ifmatm-type {
  belongs-to huawei-ifmatm {
    prefix ifmatm;
  }
  
  organization
    "Huawei Technologies Co.,Ltd.";
  contact
    "Huawei Industrial Base Bantian, Longgang Shenzhen 518129                    
        People's Republic of China                    
        Website: http://www.huawei.com Email: support@huawei.com";
  description
    "type of ifmatm";
  revision 2017-03-23 {
    description
      "Functions supported by the schema are added to the YANG file.";
    reference
      "Huawei private.";
  }
  revision 2013-01-01 {
    description
      "Init revision";
    reference
      "Huawei private.";
  }


  typedef ifmatmBool {
    type enumeration {
      enum "Disable" {
        description
          "Disable.";
      }
      enum "Enable" {
        description
          "Enable.";
      }
    }
    description
      "type of ifmatm bool";
  }

  typedef ifmatmInterfaceType {
    type enumeration {
      enum "uni" {
        description
          "ATM interface type UNI.";
      }
      enum "nni" {
        description
          "ATM interface type NNI.";
      }
    }
    description
      "type of ifmatm interface";
  }

  typedef ifmatmIfStateType {
    type enumeration {
      enum "up" {
        description
          "Interface state Up.";
      }
      enum "down" {
        description
          "Interface state Down.";
      }
    }
    description
      "type of ifmatm ifState";
  }

  typedef ifmatmAdminStaType {
    type enumeration {
      enum "up" {
        description
          "Admin state Up.";
      }
      enum "down" {
        description
          "Admin state Down.";
      }
    }
    description
      "type of ifmatm admin State";
  }

  typedef ifmatmPvcStateType {
    type enumeration {
      enum "up" {
        description
          "PVC state Up.";
      }
      enum "down" {
        description
          "PVC State Down.";
      }
    }
    description
      "type of ifmatm pvc state";
  }

  typedef ifmatmPvpStateType {
    type enumeration {
      enum "up" {
        description
          "PVP state Up.";
      }
      enum "down" {
        description
          "PVP State Down.";
      }
    }
    description
      "type of ifmatm pvp state";
  }

  typedef ifmatmMapStateType {
    type enumeration {
      enum "up" {
        description
          "MAP state Up.";
      }
      enum "down" {
        description
          "MAP State Down.";
      }
    }
    description
      "type of ifmatm map state";
  }

  typedef ifmatmPvcMapProtocolType {
    type enumeration {
      enum "ip" {
        description
          "PVC mapping protocol IP.";
      }
      enum "eth" {
        description
          "PVC mapping protocol ETH.";
      }
      enum "ppp" {
        description
          "PVC mapping protocol PPP.";
      }
      enum "none" {
        description
          "PVC mapping protocol none.";
      }
    }
    description
      "type of ifmatm pvc map protocol";
  }

  typedef ifmatmEncapType {
    type enumeration {
      enum "aal5mux" {
        description
          "PVC encapsulation AAL5-MUX.";
      }
      enum "aal5nlpid" {
        description
          "PVC encapsulation AAL5-NLPID.";
      }
      enum "aal5nlpidietf" {
        description
          "PVC encapsulation AAL5-NLPIDIETF.";
      }
      enum "aal5snap" {
        description
          "PVC encapsulation AAL5-SNAP.";
      }
    }
    description
      "type of ifmatm encap";
  }

  typedef ifmatmServeiceType {
    type enumeration {
      enum "cbr" {
        description
          "ATM service type CBR.";
      }
      enum "nrt-vbr" {
        description
          "ATM service type NRT-VBR.";
      }
      enum "rt-vbr" {
        description
          "ATM service type RT-VBR.";
      }
      enum "ubr" {
        description
          "ATM service type UBR.";
      }
      enum "ubr-plus" {
        description
          "ATM service type UBR-PLUS.";
      }
    }
    description
      "type of ifmatm serveice";
  }

  typedef ifmatmBindType {
    type enumeration {
      enum "input" {
        description
          "PVC bind type input.";
      }
      enum "output" {
        description
          "PVC bind type output.";
      }
    }
    description
      "type of ifmatm bind";
  }

  typedef ifmatmMapType {
    type enumeration {
      enum "none" {
        description
          "None.";
      }
      enum "directional" {
        description
          "Unidirectional mapping.";
      }
      enum "bidirectional" {
        description
          "Bidirectional mapping.";
      }
    }
    description
      "type of ifmatm map";
  }

  typedef ifmimaFrameLenType {
    type enumeration {
      enum "frameLength32" {
        description
          "IMA-group frame length 32.";
      }
      enum "frameLength64" {
        description
          "IMA-group frame length 64.";
      }
      enum "frameLength128" {
        description
          "IMA-group frame length 128.";
      }
      enum "frameLength256" {
        description
          "IMA-group frame length 256.";
      }
    }
    description
      "type of ifmima frame length";
  }

  typedef ifType {
    type enumeration {
      enum "mainIf" {
        description
          "Main interface.";
      }
      enum "subIf" {
        description
          "Sub-interface.";
      }
    }
    description
      "type of ifType";
  }

  typedef ifmatmCellTransBool {
    type enumeration {
      enum "Disable" {
        description
          "Disable.";
      }
      enum "Enable" {
        description
          "Enable.";
      }
    }
    description
      "type of ifmatm cell transfe";
  }

  typedef ifPhyType {
    type enumeration {
      enum "Serial" {
        description
          "Serial interface.";
      }
      enum "ATM" {
        description
          "ATM interface.";
      }
      enum "Ima-group" {
        description
          "IMA-group interface.";
      }
      enum "Trunk-Serial" {
        description
          "Trunk-Serial Interface";
      }
      enum "Global-Ima-Group" {
        description
          "Global-Ima-Group Interface";
      }
    }
    description
      "type of ifPhy";
  }

  typedef ifmatmScramble {
    type enumeration {
      enum "enabled" {
        description
          "Enabled.";
      }
      enum "disabled" {
        description
          "Disabled.";
      }
    }
    description
      "type of ifmatm scramble";
  }
}
