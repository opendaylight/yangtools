/*
Copyright (C) 2013-2017 Huawei Technologies Co., Ltd. All rights reserved.
*/
submodule huawei-dcn-action {
  belongs-to huawei-dcn {
    prefix dcn;
  }
  include huawei-dcn-type;
  
  organization
    "Huawei Technologies Co.,Ltd.";
  contact
    "Huawei Industrial Base Bantian, Longgang Shenzhen 518129                    
        People's Republic of China                    
        Website: http://www.huawei.com Email: support@huawei.com";
  description
    "DCN action";
  revision 2017-03-23 {
    description
      "Functions supported by the schema are added to the YANG file.";
    reference
      "Huawei private.";
  }
  revision 2013-01-01 {
    description
      "Init revision";
    reference
      "Huawei private.";
  }
  rpc nmsAttr {
    description
      "NMS attribute.";
    input {
      leaf nmsAttr {
        type uint32 {
          range "0..4294967295";
        }
        description
          "NMS attribute.";
      }
    }
  }
}
