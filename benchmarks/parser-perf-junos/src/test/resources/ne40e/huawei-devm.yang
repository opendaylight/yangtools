/*
Copyright (C) 2013-2017 Huawei Technologies Co., Ltd. All rights reserved.
*/
module huawei-devm {
  namespace "http://www.huawei.com/netconf/vrp/huawei-devm";
  prefix devm;
  import huawei-ifm {
    prefix ifm;
  }
  import huawei-pub-type {
    prefix pub-type;
  }
  import ietf-yang-types {
    prefix yang;
  }
  import huawei-extension {
    prefix ext;
  }
  include huawei-devm-action;
  include huawei-devm-type;
  
  organization
    "Huawei Technologies Co.,Ltd.";
  contact
    "Huawei Industrial Base Bantian, Longgang Shenzhen 518129                    
        People's Republic of China                    
        Website: http://www.huawei.com Email: support@huawei.com";
  description
    "Global Configuration.";
  revision 2017-03-23 {
    description
      "Functions supported by the schema are added to the YANG file.";
    reference
      "Huawei private.";
  }
  revision 2013-01-01 {
    description
      "Init revision";
    reference
      "Huawei private.";
  }
  container devm {
    description
      "Global Configuration.";
    container globalPara {
      description
        "Global configuration.";
      leaf maxChassisNum {
        type uint32 {
          range "1..255";
        }
        config false;
        description
          "Maximum number of chassis.";
      }
      leaf chassisNum {
        type uint32;
        config false;
        description
          "Current number of chassis.";
      }
      leaf chassisLastChange {
        type pub-type:timeTick;
        config false;
        description
          "Time when a chassis or an entity is last added or removed, or time when chassis status (administration status, running status, or active/standby status) is last changed. The time is in UTC time.";
      }
      leaf crcEnable {
        type boolean;
        default "true";
        description
          "Enalbe or disable the crc error monitor.";
        ext:allowDelete "true";
      }
      leaf symbolEnable {
        type boolean;
        default "true";
        description
          "Enalbe or disable the symbol error monitor.";
        ext:allowDelete "true";
      }
      leaf inputEnable {
        type boolean;
        default "true";
        description
          "Enalbe or disable the input error monitor.";
        ext:allowDelete "true";
      }
      leaf outputEnable {
        type boolean;
        default "true";
        description
          "Enalbe or disable the Output error monitor.";
        ext:allowDelete "true";
      }
      leaf sdhEnable {
        type boolean;
        default "true";
        description
          "Enalbe or disable the sdh error monitor.";
        ext:allowDelete "true";
      }
      leaf bip8SdEnable {
        type boolean;
        default "true";
        description
          "Enalbe or disable the BIP8-SD error monitor.";
        ext:allowDelete "true";
      }
      leaf badbytesEnable {
        type boolean;
        default "true";
        description
          "Enalbe or disable the Bad-Bytes error monitor.";
        ext:allowDelete "true";
      }
      leaf opticalEnable {
        type boolean;
        default "true";
        description
          "Enalbe or disable the optical module abnormal monitor.";
        ext:allowDelete "true";
      }
      leaf txPauseEnable {
        type boolean;
        default "true";
        description
          "Enalbe or disable the tx-pause error monitor.";
        ext:allowDelete "true";
      }
      leaf sysTrapType {
        type devmTrapType;
        description
          "Switch trapType between base-trap and dc-trap.";
        ext:allowDelete "true";
      }
      leaf curWorkMode {
        type devmSysWorkType;
        default "non-redundant";
        config false;
        description
          "Cur work mode, 1+1 or 1:1.";
      }
      leaf nextWorkMode {
        type devmSysWorkType;
        default "non-redundant";
        description
          "Next work mode,1+1 or 1:1(waring:system will restart after success,and then take effect).";
      }
      leaf curForwardMode {
        type devmForwardWorkType;
        default "compatible";
        config false;
        description
          "Cur Forward mode, compatible or enhance.";
      }
      leaf nextForwardMode {
        type devmForwardWorkType;
        default "compatible";
        description
          "Next Forward mode,compatible or enhance(waring:system will restart after success,and then take effect).";
      }
      leaf energyMode {
        type energyModeType;
        default "basic";
        description
          "Energy-saving Mode(which includes basic,standard,deep,optimal. The default value is basic).";
      }
      leaf warmBackUpModeCfg {
        type warmBackUpModeCfgType;
        default "disable";
        description
          "Cur warm-backup mode";
      }
      leaf warmBackUpModeSts {
        type warmBackUpModeStsType;
        default "off";
        config false;
        description
          "Cur warm-backup status";
      }
      leaf brdRstCtrlMode {
        type boolean;
        default "true";
        description
          "Enable Board Abnormal Reset Detection.";
        ext:allowDelete "true";
      }
      leaf crdRstCtrlMode {
        type boolean;
        default "true";
        description
          "Enable Card Abnormal Reset Detection.";
        ext:allowDelete "true";
      }
      leaf systemServiceType {
        type string {
          length "0..128";
        }
        config false;
        description
          "System Service Type.";
      }
      leaf loopBackClear {
        type boolean;
        default "false";
        description
          "Enable or disable the loop auto-clear function.";
      }
      leaf loopBackClearPd {
        type uint32 {
          range "1..2880";
        }
        default "5";
        description
          "The period of loop auto-clear function.";
      }
      leaf portBandwidthType {
        type portBandwidthType;
        default "DataLink";
        description
          "Port Bandwidth Type.";
      }
      leaf highTempSwitch {
        type devmBool;
        default "YES";
        description
          "High Temperature Switch.";
      }
      leaf autoUpgradeModel {
        type boolean;
        default "true";
        description
          "Auto Upgrade Model.";
      }
      leaf tempQueryMode {
        type mibQueryModeType;
        default "default";
        description
          "MIB Temperatue Brief Query Mode.";
      }
      leaf vltQueryMode {
        type mibQueryModeType;
        default "default";
        description
          "MIB Voltage Brief Query Mode.";
      }
      leaf switchPortMode {
        type string {
          length "0..128";
        }
        config false;
        description
          "Switch-port Work-mode.";
      }
      leaf brdpowondelay {
        type uint32 {
          range "0..65535";
        }
        default "0";
        description
          "Board Power-on-delay.";
      }
      leaf crdpowondelay {
        type uint32 {
          range "0..65535";
        }
        default "0";
        description
          "Pic Power-on-delay.";
      }
      leaf cposMixSevMode {
        type boolean;
        default "false";
        description
          "Cpos-card mixed service enable.";
      }
      leaf sfuSwitchMode {
        type sfuSwitchModeType;
        default "disable";
        description
          "SfuSwitchMode.";
      }
      leaf splitFlag {
        type devmSplitResumeModeType;
        must "not(../splitFlag='NotSupport') or ((not(../splitFlag='NotSupport') and (../splitFlag='SlaveReset' or ../splitFlag='FastPreemption') ))";
        default "SlaveReset";
        description
          "Slave chassis reset mode.";
      }
    }
    container phyEntitys {
      config false;
      description
        "Summary of the information about physical entities.";
      list phyEntity {
        key "entClass position entSerialNo";
        config false;
        description
          "Summary of the information about physical entities.";
        leaf entClass {
          type devmEntityClassType;
          config false;
          description
            "Entity class.";
        }
        leaf position {
          type string {
            length "0..32";
          }
          config false;
          description
            "Entity position.";
        }
        leaf entSerialNo {
          type string {
            length "0..32";
          }
          config false;
          description
            "Entity number.";
        }
        leaf entIndex {
          type uint32;
          config false;
          description
            "Entity index.";
        }
        leaf chassisIndex {
          type uint32;
          config false;
          description
            "Chassis index.";
        }
        leaf boardIndex {
          type uint32;
          config false;
          description
            "Board index.";
        }
        leaf entName {
          type string {
            length "0..128";
          }
          config false;
          description
            "Entity name.";
        }
        leaf entDescr {
          type string {
            length "0..256";
          }
          config false;
          description
            "Entity description.";
        }
        leaf entAlias {
          type string {
            length "0..128";
          }
          config false;
          description
            "Entity alias.";
        }
        leaf entVendorType {
          type devmHardType;
          config false;
          description
            "Type of a hardware entity.";
        }
        leaf entContainedIn {
          type uint32;
          config false;
          description
            "Information about the parent index of an entity.";
        }
        leaf entParentRelPos {
          type uint32;
          config false;
          description
            "Position of an entity relative to its parent entity.  ";
        }
        leaf entHardwareRev {
          type string {
            length "0..128";
          }
          config false;
          description
            "Hardware version.";
        }
        leaf entFirmwareRev {
          type string {
            length "0..128";
          }
          config false;
          description
            "Firmware version.";
        }
        leaf entSoftwareRev {
          type string {
            length "0..128";
          }
          config false;
          description
            "Software version.";
        }
        leaf entModelName {
          type string {
            length "0..128";
          }
          config false;
          description
            "Module name.";
        }
        leaf entIsFRU {
          type boolean;
          config false;
          description
            "Whether the entity a replaceable unit.";
        }
        leaf entAdminState {
          type devmEntityAdminState;
          config false;
          description
            "Administration state (read-write).";
        }
        leaf entOperState {
          type devmEntityOperState;
          config false;
          description
            "Operation state of an entity (read-only).";
        }
        leaf entStandbyState {
          type devmEntityStandbyState;
          config false;
          description
            "Active/standby state.";
        }
        leaf entSystemOid {
          type string {
            length "0..128";
          }
          config false;
          description
            "Entity OID.";
        }
        leaf entLsName {
          type string {
            length "0..32";
          }
          config false;
          description
            "The LS name of the entity.";
        }
      }
    }
    container chassiss {
      description
        "Chassis.";
      list chassis {
        key "position";
        description
          "Chassis.";
        leaf position {
          type string {
            length "0..32";
          }
          description
            "Chassis position.";
        }
        leaf entIndex {
          type uint32;
          config false;
          description
            "Chassis index.";
        }
        leaf chassisType {
          type devmChassisType;
          config false;
          description
            "Chassis type.";
        }
        leaf serviceType {
          type devmChassisSvcType;
          config false;
          description
            "Chassis service type.";
        }
        leaf slotNum {
          type uint32;
          config false;
          description
            "Number of slots on a chassis.";
        }
        leaf boardNum {
          type uint32;
          config false;
          description
            "Number of boards on a chassis.";
        }
        leaf fanNum {
          type uint32;
          config false;
          description
            "Number of fans on a chassis.";
        }
        leaf powerNum {
          type uint32;
          config false;
          description
            "Number of power supplies for a chassis.";
        }
        leaf upTime {
          type pub-type:timeTick;
          config false;
          description
            "Up time of a chassis.";
        }
        leaf statusLastChange {
          type pub-type:timeTick;
          config false;
          description
            "Timetick that indicates entity status changes.";
        }
        leaf entityLastChange {
          type pub-type:timeTick;
          config false;
          description
            "Timetick that indicates entity on chassis changes.";
        }
        leaf curChassisID {
          type uint32 {
            range "1..8";
          }
          config false;
          description
            "Current Chassis ID.";
        }
        leaf nextChassisID {
          type uint32 {
            range "1..8";
          }
          default "1";
          description
            "Next run Chassis ID.";
        }
        leaf curRunMode {
          type devmProductType;
          config false;
          description
            "Current Run Mode.";
        }
        leaf nextRunMode {
          type devmProductType;
          description
            "Next Run Mode.";
          ext:allowDelete "true";
        }
        leaf dustCleanCycle {
          type uint32 {
            range "0..65535";
          }
          units day;
          default "90";
          description
            "Dust Clean Cycle(Days).";
          ext:allowDelete "true";
        }
        leaf lastCleanDate {
          type string {
            length "0..128";
          }
          config false;
          description
            "Last Clean Date.";
        }
        leaf upToLastClean {
          type uint32 {
            range "0..4294967295";
          }
          default "0";
          config false;
          description
            "Up To Last Clean(Days).";
        }
        leaf alarmExistDays {
          type uint32 {
            range "0..4294967295";
          }
          default "0";
          config false;
          description
            "Alarm Exist Days.";
        }
        container monitorBoardChanges {
          config false;
          description
            "Timetick that indicates board status changes.";
          list monitorBoardChange {
            key "boardIndex";
            config false;
            description
              "Timetick that indicates board status changes.";
            leaf boardIndex {
              type uint32;
              config false;
              description
                "Board index.";
            }
            leaf statusLastChange {
              type pub-type:timeTick;
              config false;
              description
                "Timetick that indicates board status changes.";
            }
            leaf entityLastChange {
              type pub-type:timeTick;
              config false;
              description
                "Timetick that indicates entity on board changes.";
            }
          }
        }
        container halfChassises {
          description
            "Half Chassis";
          list halfChassis {
            key "halfChassisPos";
            max-elements  "2";
            description
              "Half Chassis";
            leaf halfChassisPos {
              type devmHalfChassisPos;
              description
                "Position of Half Chassis";
            }
            leaf fiberConnType {
              type devmFiberConnType;
              default "halfFabric";
              description
                "Fiber Connection Type";
            }
            leaf nextRunFiberConnType {
              type devmFiberConnType;
              default "halfFabric";
              description
                "Fiber Connection Type on Next Running Time";
            }
            leaf trafficState {
              type devmTrafficState;
              default "open";
              description
                "Half Chassis Traffic State ";
            }
          }
        }
        container powerSupplyInfo {
          description
            "Power supply info";
          leaf powerSupplyLim {
            type uint32 {
              range "1..4294967295";
            }
            config false;
            description
              "Limit Power";
          }
          leaf powerSupplyMode {
            type pwrSupplyModeType;
            default "standard";
            description
              "Power supply mode";
          }
          leaf powerSupplyVal {
            when "not(../powerSupplyMode!='assign')";
            type uint32 {
              range "0..11200";
            }
            default "0";
            description
              "Power supply input power";
          }
          leaf powerSupplyAss {
            type uint32;
            default "0";
            config false;
            description
              "Assigned Power";
          }
          leaf powerSupplyAsUt {
            type string {
              length "0..255";
            }
            default "0";
            config false;
            description
              "Assigned Power Utility";
          }
          leaf powerSupplyLeft {
            type int32;
            default "0";
            config false;
            description
              "Left Power";
          }
          leaf powerSupplyReal {
            type uint32;
            config false;
            description
              "Real Power";
          }
          leaf powerSupplyReUt {
            type string {
              length "0..255";
            }
            default "0";
            config false;
            description
              "Real Power Utility";
          }
          leaf powerSupplyTemp {
            when "../powerSupplyMode!='assign'";
            type pwrSupplyTempType;
            default "temphigh";
            description
              "Termperature";
          }
          leaf pmOutputLimVal {
            type uint32 {
              range "0..4294967295";
            }
            default "0";
            description
              "PM output limited value.";
            ext:allowDelete "true";
          }
        }
      }
    }
    container containers {
      description
        "Slots.";
      list container {
        key "position";
        description
          "Slot.";
        leaf position {
          type string {
            length "0..32";
          }
          description
            "Slot position.";
        }
        leaf entIndex {
          type uint32;
          config false;
          description
            "Slot index.";
        }
        leaf containerType {
          type devmContainerType;
          config false;
          description
            "Slot type.";
        }
        leaf equipedEntityType {
          type devmHardType;
          config false;
          description
            "Type of an equipped entity. ";
        }
        container veMacAddress {
          description
            "VE Mac address.";
          leaf l2VeMac {
            type pub-type:macAddress {
              length "0..255";
            }
            description
              "L2 VE Mac.";
          }
          leaf accessVeMac {
            type pub-type:macAddress {
              length "0..255";
            }
            description
              "Access VE mac.";
          }
        }
      }
    }
    container mpuBoards {
      description
        "MPUs.";
      list mpuBoard {
        key "position";
        description
          "MPU.";
        leaf position {
          type string {
            length "0..32";
          }
          description
            "MPU position.";
        }
        leaf entIndex {
          type uint32;
          config false;
          description
            "MPU index.";
        }
        leaf boardType {
          type devmBoardType;
          config false;
          description
            "MPU type.";
        }
        leaf upTime {
          type pub-type:timeTick;
          config false;
          description
            "Up time of an MPU, the unit is timetick.";
        }
        leaf sdramSize {
          type uint32;
          units "M Bytes";
          config false;
          description
            "SDRAM size.";
        }
        leaf nvramSize {
          type uint32;
          units "M Bytes";
          config false;
          description
            "NVRAM size, the unit is KB.";
        }
        leaf flashSize {
          type uint32;
          units "M Bytes";
          config false;
          description
            "Flash size.";
        }
        leaf lsRole {
          type devmLsRole;
          config false;
          description
            "MPU role.";
        }
        leaf lastResetTime {
          type yang:date-and-time;
          config false;
          description
            "Time of last reset.";
        }
        leaf lastResetReason {
          type string {
            length "0..256";
          }
          config false;
          description
            "Reason of last reset.";
        }
        container slotFwdModeMp {
          description
            "Slot Forward Mode";
          leaf forwardMode {
            type slotForwardModeType;
            default "Loopback";
            description
              "Forward Mode";
          }
        }
        container slotMacMtuDiscardStatMp {
          config false;
          description
            "MAC&MTU error statistics.";
          leaf statisticsMtuIpv4 {
            type uint64;
            config false;
            mandatory true;
            description
              "IPv4 MTU error statistics.";
          }
          leaf statisticsMtuIpv6 {
            type uint64;
            config false;
            mandatory true;
            description
              "IPv6 MTU error statistics.";
          }
          leaf statisticsMacIpv4 {
            type uint64;
            config false;
            mandatory true;
            description
              "IPv4 MAC error statistics.";
          }
          leaf statisticsMacIpv6 {
            type uint64;
            config false;
            mandatory true;
            description
              "IPv6 MAC error statistics.";
          }
        }
        container mpuquePriority {
          description
            "MAC Queue Priority Enable.";
          leaf queuePriEnable {
            type devmQueuePriorityType;
            default "enable";
            description
              "MAC Queue Priority Enable.";
            ext:allowDelete "true";
          }
        }
        container slotLinkProtCfgMp {
          description
            "Transparent transmission of link-layer protocol information.";
          leaf protocolLldp {
            type slotLinkProtCfgState;
            description
              "Link Layer Discovery Protocol.";
            ext:allowDelete "true";
          }
          leaf protocolLacp {
            type slotLinkProtCfgState;
            description
              "Link Aggregation Control Protocol.";
            ext:allowDelete "true";
          }
          leaf protocolOam {
            type slotLinkProtCfgState;
            description
              "Operation,Administration and Maintenance Protocol.";
            ext:allowDelete "true";
          }
          leaf protocolEsmc {
            type slotLinkProtCfgState;
            description
              "Ethernet Synchronization Messaging Channel.";
            ext:allowDelete "true";
          }
        }
      }
    }
    container lpuBoards {
      description
        "LPUs.";
      list lpuBoard {
        key "position";
        description
          "LPU.";
        leaf position {
          type string {
            length "0..32";
          }
          description
            "LPU position.";
        }
        leaf entIndex {
          type uint32;
          config false;
          description
            "LPU index.";
        }
        leaf boardType {
          type devmBoardType;
          config false;
          description
            "LPU type.";
        }
        leaf sdramSize {
          type uint32;
          units "M Bytes";
          config false;
          description
            "SDRAM size.";
        }
        leaf flashSize {
          type uint32;
          units "M Bytes";
          config false;
          description
            "Flash size.";
        }
        leaf upTime {
          type pub-type:timeTick;
          config false;
          description
            "Up time of an LPU, the unit is timetick.";
        }
        leaf npRDRAMSize {
          type uint32;
          units "M Bytes";
          config false;
          description
            "NP RDRAM size.";
        }
        leaf npSRAMSize {
          type uint32;
          units "M Bytes";
          config false;
          description
            "NP SRAM size.";
        }
        leaf serviceType {
          type devmLpuServiceType;
          config false;
          description
            "Service type.";
        }
        leaf nextServiceType {
          type devmLpuServiceType;
          config false;
          description
            "Type of next started service board.";
        }
        leaf picNum {
          type uint32;
          config false;
          description
            "Number of PICs on an LPU.";
        }
        leaf subSlotNum {
          type uint32;
          config false;
          description
            "Number of slots on a subcard.";
        }
        leaf clock8kPort {
          type leafref {
            path "/devm/ports/port/position";
          }
          description
            "8K clock port.";
        }
        leaf curL3Clk {
          type uint32;
          config false;
          description
            "Current L3 clock source.";
        }
        container l3Clocks {
          config false;
          description
            "L3 clocks.";
          list l3Clock {
            key "clockID";
            config false;
            description
              "L3 clock.";
            leaf clockID {
              type string {
                length "0..255";
              }
              config false;
              description
                "L3 clock ID.";
            }
            leaf l3ClkState {
              type devmClockSrcStatusType;
              config false;
              description
                "L3 clock state.";
            }
          }
        }
        container slotFwdMode {
          description
            "Slot Forward Mode";
          leaf forwardMode {
            type slotForwardModeType;
            default "Loopback";
            description
              "Forward Mode";
          }
        }
        container slotMacMtuDiscardStat {
          config false;
          description
            "MAC&MTU error statistics.";
          leaf statisticsMtuIpv4 {
            type uint64;
            config false;
            mandatory true;
            description
              "IPv4 MTU error statistics.";
          }
          leaf statisticsMtuIpv6 {
            type uint64;
            config false;
            mandatory true;
            description
              "IPv6 MTU error statistics.";
          }
          leaf statisticsMacIpv4 {
            type uint64;
            config false;
            mandatory true;
            description
              "IPv4 MAC error statistics.";
          }
          leaf statisticsMacIpv6 {
            type uint64;
            config false;
            mandatory true;
            description
              "IPv6 MAC error statistics.";
          }
        }
        container slotMacSyn {
          description
            "Slot MAC Synchronize ";
          leaf synEnable {
            type boolean;
            default "false";
            description
              "MAC Synchronize Enable";
          }
        }
        container lpuquePriority {
          description
            "MAC Queue Priority Enable.";
          leaf queuePriEnable {
            type devmQueuePriorityType;
            default "enable";
            description
              "MAC Queue Priority Enable.";
            ext:allowDelete "true";
          }
        }
        container slotLinkProtCfg {
          description
            "Transparent transmission of link-layer protocol information.";
          leaf protocolLldp {
            type slotLinkProtCfgState;
            description
              "Link Layer Discovery Protocol.";
            ext:allowDelete "true";
          }
          leaf protocolLacp {
            type slotLinkProtCfgState;
            description
              "Link Aggregation Control Protocol.";
            ext:allowDelete "true";
          }
          leaf protocolOam {
            type slotLinkProtCfgState;
            description
              "Operation,Administration and Maintenance Protocol.";
            ext:allowDelete "true";
          }
          leaf protocolEsmc {
            type slotLinkProtCfgState;
            description
              "Ethernet Synchronization Messaging Channel.";
            ext:allowDelete "true";
          }
        }
      }
    }
    container sfuBoards {
      config false;
      description
        "SFUs.";
      list sfuBoard {
        key "position";
        config false;
        description
          "SFU.";
        leaf position {
          type string {
            length "0..32";
          }
          config false;
          description
            "SFU position.";
        }
        leaf entIndex {
          type uint32;
          config false;
          description
            "SFU index.";
        }
        leaf boardType {
          type devmBoardType;
          config false;
          description
            "SFU type.";
        }
        leaf sdramSize {
          type uint32;
          units "M Bytes";
          config false;
          description
            "SDRAM size.";
        }
        leaf flashSize {
          type uint32;
          units "M Bytes";
          config false;
          description
            "Flash size.";
        }
        leaf upTime {
          type pub-type:timeTick;
          config false;
          description
            "Up time of an SFU, the unit is timetick.";
        }
      }
    }
    container ecuBoards {
      config false;
      description
        "ECU boards.";
      list ecuBoard {
        key "position";
        config false;
        description
          "ECU board.";
        leaf position {
          type string {
            length "0..32";
          }
          config false;
          description
            "ECU position.";
        }
        leaf entIndex {
          type uint32;
          config false;
          description
            "ECU index.";
        }
        leaf boardType {
          type devmBoardType;
          config false;
          mandatory true;
          description
            "ECU type.";
        }
        leaf sdramSize {
          type uint32;
          units "M Bytes";
          config false;
          description
            "SDRAM size.";
        }
        leaf flashSize {
          type uint32;
          units "M Bytes";
          config false;
          description
            "Flash size.";
        }
        leaf upTime {
          type pub-type:timeTick;
          config false;
          description
            "Up time of an ECU, the unit is timetick.";
        }
        leaf ofcCardNum {
          type uint32;
          config false;
          description
            "Number of OFC cards.";
        }
        leaf subSlotNum {
          type uint32;
          config false;
          description
            "Number of slots on a subcard. ";
        }
      }
    }
    container icuBoards {
      config false;
      description
        "ICUs.";
      list icuBoard {
        key "position";
        config false;
        description
          "ICU board.";
        leaf position {
          type string {
            length "0..32";
          }
          config false;
          description
            "ICU position.";
        }
        leaf entIndex {
          type uint32;
          config false;
          description
            "ICU index.";
        }
        leaf boardType {
          type devmBoardType;
          config false;
          mandatory true;
          description
            "ICU type.";
        }
        leaf sdramSize {
          type uint32;
          units "M Bytes";
          config false;
          description
            "SDRAM size.";
        }
        leaf flashSize {
          type uint32;
          units "M Bytes";
          config false;
          description
            "Flash size.";
        }
        leaf upTime {
          type pub-type:timeTick;
          config false;
          description
            "Up time of an ICU, the unit is timetick.";
        }
      }
    }
    container clockBoards {
      description
        "Clock boards.";
      list clockBoard {
        key "position";
        description
          "Clock board.";
        leaf position {
          type string {
            length "0..32";
          }
          description
            "Clock board position.";
        }
        leaf entIndex {
          type uint32;
          config false;
          description
            "Clock board index.";
        }
        leaf boardType {
          type devmBoardType;
          config false;
          description
            "Type of a clock board.";
        }
        leaf upTime {
          type pub-type:timeTick;
          config false;
          description
            "Up time of a clock board, the unit is timetick.";
        }
        leaf sramState {
          type devmRunState;
          config false;
          description
            "SRAM state.";
        }
        leaf singleState388M {
          type devmRunState;
          config false;
          description
            "38.8M clock state.";
        }
        leaf lockRingState {
          type devmRunState;
          config false;
          description
            "PLL state.";
        }
        leaf lockRing88State {
          type devmRunState;
          config false;
          description
            "88M PLL state.";
        }
        leaf oscState {
          type devmRunState;
          config false;
          description
            "OSC state.";
        }
        leaf i2cBusState {
          type devmRunState;
          config false;
          description
            "I2C bus state.";
        }
        leaf epldState {
          type devmRunState;
          config false;
          description
            "Logic state.";
        }
        leaf hdlcState {
          type devmRunState;
          config false;
          description
            "HDLC state.";
        }
        leaf e1AState {
          type devmRunState;
          config false;
          description
            "E1A state.";
        }
        leaf e1BState {
          type devmRunState;
          config false;
          description
            "E1B state.";
        }
        container clock {
          description
            "Clock.";
          leaf currentWorkMode {
            type devmWorkMode;
            default "auto";
            description
              "Working mode of the current clock.";
          }
          leaf currentSource {
            type leafref {
              path "/devm/clockBoards/clockBoard/clockSources/clockSource/clockSrcID";
            }
            must "../currentWorkMode='manual'";
            default "0";
            description
              "Current clock source.";
          }
          leaf clkOutSSM {
            type devmSsmlevel;
            config false;
            description
              "Out SSM level.";
          }
          leaf ssmControl {
            type devmControlFlag;
            default "on";
            description
              "SSM selection identifier.";
          }
          leaf hardWorkState {
            type devmRunState;
            config false;
            description
              "Working state of a clock.";
          }
        }
        container clockSources {
          description
            "Clock sources.";
          list clockSource {
            key "clockSrcID";
            description
              "Clock source.";
            leaf clockSrcID {
              type uint32;
              description
                "Clock Source ID.";
            }
            leaf priority {
              type uint32 {
                range "1..19";
              }
              default "19";
              description
                "Clock source priority.";
            }
            leaf description {
              type string {
                length "0..255";
              }
              config false;
              description
                "Clock source description.";
            }
            leaf sabit {
              type devmClockSabitType;
              default "unknown";
              description
                "Bit of the BITS clock source timeslot.";
            }
            leaf forcessm {
              type devmClockForceSsmType;
              default "on";
              description
                "Forceful enabling and disabling for SSM learning. ";
            }
            leaf ssmLevel {
              type devmSsmlevel;
              must "../forcessm='off'";
              default "unknown";
              description
                "SSM level.";
            }
            leaf state {
              type string {
                length "0..255";
              }
              config false;
              description
                "Clock source state.";
            }
            leaf bitsType {
              type devmClkBitsType;
              must "not(../clockSrcID='1' and ../clockSrcID='2')";
              default "2mbps";
              description
                "Bits type.";
            }
            leaf bitsMap {
              type devmClkBitsMap;
              must "not(../clockSrcID='1' and ../clockSrcID='2')";
              default "bits0";
              description
                "Bits map.";
            }
          }
        }
      }
    }
    container pmus {
      config false;
      description
        "PMU.";
      list pmu {
        key "position";
        config false;
        description
          "PMU.";
        leaf position {
          type string {
            length "0..32";
          }
          config false;
          description
            "PMU position.";
        }
        leaf entIndex {
          type uint32;
          config false;
          description
            "PMU index.";
        }
        leaf boardType {
          type devmBoardType;
          config false;
          description
            "Type of a PMU board.";
        }
        leaf present {
          type string {
            length "0..16";
          }
          config false;
          description
            "Present.";
        }
        leaf haStatus {
          type string {
            length "0..16";
          }
          config false;
          description
            "HaStatus.";
        }
        leaf register {
          type string {
            length "0..16";
          }
          config false;
          description
            "Register.";
        }
        leaf work {
          type string {
            length "0..16";
          }
          config false;
          description
            "Work.";
        }
      }
    }
    container cmus {
      description
        "CMUs.";
      list cmu {
        key "position";
        description
          "CMU.";
        leaf position {
          type string {
            length "0..32";
          }
          description
            "CMU position. ";
        }
        leaf entIndex {
          type uint32;
          config false;
          description
            "CMU supply index.";
        }
        leaf boardType {
          type devmHardType;
          config false;
          description
            "Type of a CMU board.";
        }
        container cmuSwitchs {
          description
            "CMU Switch.";
          list cmuSwitch {
            key "cmuSwitchID";
            description
              "CMU Switch.";
            leaf cmuSwitchID {
              type uint32 {
                range "0..6";
              }
              description
                "Switch ID.";
            }
            leaf cmuSwitchName {
              type string {
                length "1..24";
              }
              description
                "Switch Name.";
            }
            leaf cmuAlmMode {
              type devmCmuAlmMode;
              default "undo";
              description
                "Alarm Mode.";
            }
            leaf cmuSwitchFog {
              type devmCmuSwitchFog;
              default "unknown";
              description
                "Object.";
              ext:allowDelete "true";
            }
          }
        }
        container cmuRelays {
          description
            "CMU Relays.";
          list cmuRelay {
            key "cmuRelayID";
            description
              "CMU Relay.";
            leaf cmuRelayID {
              type uint32 {
                range "0..1";
              }
              description
                "Ralay ID.";
            }
            leaf cmuRelayName {
              type string {
                length "1..24";
              }
              description
                "Relay Name.";
            }
            leaf cmuRelayAlmMode {
              type devmCmuAlmMode;
              default "undo";
              description
                "Alarm Mode.";
            }
          }
        }
        container cmuAnalogs {
          description
            "CMU Analogs.";
          list cmuAnalog {
            key "cmuAnalogID";
            description
              "CMU Analog.";
            leaf cmuAnalogID {
              type uint32 {
                range "0..1";
              }
              description
                "CMU Analog ID.";
            }
            leaf cmuAnalogName {
              type string {
                length "1..23";
              }
              description
                "CMU Analog Name.";
            }
            leaf cmuAnalogType {
              type devmAnalogType;
              default "unknown";
              description
                "Specify cmu analog sensor type.";
            }
            leaf cmuAnalogObject {
              type devmAnalogObjectType;
              default "unknown";
              description
                "Specify object monitored by this cmu analog sensor.";
            }
            leaf cmuWorkLow {
              type int32 {
                range "-99999999..999999999";
              }
              default "0";
              description
                "Specify cmu analog workLow.";
            }
            leaf cmuWorkHigh {
              type int32 {
                range "-99999999..999999999";
              }
              default "0";
              description
                "Specify cmu analog workHigh.";
            }
            leaf cmuWanted {
              type int32 {
                range "-99999999..999999999";
              }
              default "0";
              description
                "Specify cmu analog cmuWanted.";
            }
            leaf cmuAlarmLow {
              type int32 {
                range "-99999999..999999999";
              }
              default "0";
              description
                "Specify cmu analog alrmLow.";
            }
            leaf cmuAlarmHigh {
              type int32 {
                range "-99999999..999999999";
              }
              default "0";
              description
                "Specify cmu analog alarmHigh.";
            }
          }
        }
        container cmuAlarms {
          description
            "CMU alarms.";
          list cmuAlarm {
            key "cmuAlarmID";
            description
              "CMU alarm.";
            leaf cmuAlarmID {
              type uint32 {
                range "0..1";
              }
              description
                "CMU alarm ID";
            }
            leaf cmuAlarmLevel {
              type devmCmuAlmMode;
              default "undo";
              description
                "Alarm Level.";
            }
          }
        }
      }
    }
    container fans {
      description
        "Fans.";
      list fan {
        key "position";
        description
          "Fan.";
        leaf position {
          type string {
            length "0..32";
          }
          description
            "Fan position.";
        }
        leaf entIndex {
          type uint32;
          config false;
          description
            "Fan index.";
        }
        leaf boardType {
          type devmBoardType;
          config false;
          description
            "Type of a fan board.";
        }
        leaf workMode {
          type devmWorkMode;
          default "auto";
          description
            "Fan working mode.";
        }
        leaf speed {
          type uint32 {
            range "0..100";
          }
          units "number of rotations";
          default "0";
          description
            "Fan speed that is a percentage of the highest speed.";
        }
        leaf fanRate {
          type uint32;
          units R/min;
          config false;
          description
            "Fan rate is the rotation per minute.";
        }
        leaf monitorCableState {
          type devmCableState;
          config false;
          description
            "State of a fan monitor cable. ";
        }
        leaf register {
          type boolean;
          default "true";
          config false;
          description
            "Fan register. ";
        }
        leaf present {
          type boolean;
          default "true";
          config false;
          description
            "Fan present.";
        }
        leaf fanNum {
          type uint32;
          config false;
          description
            "Fan number.";
        }
        leaf fanGrpSpdRps {
          type string {
            length "0..128";
          }
          default "NA";
          config false;
          description
            "Fan global speed.";
        }
      }
    }
    container powerSupplys {
      config false;
      description
        "Power supplies for a fan.";
      list powerSupply {
        key "position";
        config false;
        description
          "Power supply for a fan.";
        leaf position {
          type string {
            length "0..32";
          }
          config false;
          description
            "Power supply position. ";
        }
        leaf entIndex {
          type uint32;
          config false;
          description
            "Power supply index.";
        }
        leaf boardType {
          type devmBoardType;
          config false;
          description
            "Type of a power supply board.";
        }
        leaf workMode {
          type devmPowerWorkMode;
          config false;
          description
            "Working mode of a power supply board. ";
        }
        leaf monitorCableState {
          type devmCableState;
          config false;
          description
            "State of a power supply monitor cable. ";
        }
        leaf powerState {
          type string {
            length "0..255";
          }
          config false;
          description
            "Power Running State.";
        }
        leaf abnormaNum {
          type uint32;
          config false;
          description
            "Abnormal PowerModule Number.";
        }
        leaf normalNum {
          type uint32;
          config false;
          description
            "Normal PowerModule Number.";
        }
        container powerEnvironments {
          config false;
          description
            "Power Environment information.";
          list powerEnvironment {
            key "pemIndex";
            config false;
            description
              "Power Environment information.";
            leaf pemIndex {
              type uint32;
              config false;
              description
                "Pem Index.";
            }
            leaf voltageValue {
              type string {
                length "0..255";
              }
              config false;
              description
                "Current voltage value.";
            }
            leaf electricalValue {
              type string {
                length "0..255";
              }
              config false;
              description
                "Current electrical value.";
            }
            leaf temperValue {
              type string {
                length "0..255";
              }
              config false;
              description
                "Current Temperature value.";
            }
          }
        }
      }
    }
    container pms {
      description
        "PM.";
      list pm {
        key "position serialNo";
        description
          "PM.";
        leaf position {
          type string {
            length "0..32";
          }
          description
            "PM position.";
        }
        leaf serialNo {
          type uint32;
          description
            "Serial Number.";
        }
        leaf pmArea {
          type string {
            length "0..16";
          }
          config false;
          description
            "PM area.";
        }
        leaf entIndex {
          type uint32;
          config false;
          description
            "PM index.";
        }
        leaf boardType {
          type devmBoardType;
          config false;
          description
            "Type of a PM board.";
        }
        leaf monitorCableState {
          type devmCableState;
          config false;
          description
            "State of a PM monitor cable. ";
        }
        leaf inVol {
          type string {
            length "0..255";
          }
          config false;
          description
            "Input voltage value.";
        }
        leaf inCur {
          type string {
            length "0..255";
          }
          config false;
          description
            "Input electrical value.";
        }
        leaf inPwr {
          type string {
            length "0..255";
          }
          config false;
          description
            "Input power.";
        }
        leaf outVol {
          type string {
            length "0..255";
          }
          config false;
          description
            "Output voltage value.";
        }
        leaf outCur {
          type string {
            length "0..255";
          }
          config false;
          description
            "Output electrical value.";
        }
        leaf outPwr {
          type string {
            length "0..255";
          }
          config false;
          description
            "Output power.";
        }
        leaf singleInput {
          type devmSingleInputType;
          description
            "Set Single Input.";
          ext:allowDelete "true";
        }
      }
    }
    container lcds {
      config false;
      description
        "LCDs.";
      list lcd {
        key "position";
        config false;
        description
          "LCD.";
        leaf position {
          type string {
            length "0..32";
          }
          config false;
          description
            "Lcd position. ";
        }
        leaf entIndex {
          type uint32;
          config false;
          description
            "Lcd supply index.";
        }
        leaf boardType {
          type devmBoardType;
          config false;
          description
            "Type of a LCD board.";
        }
      }
    }
    container flexibleCards {
      description
        "Flexible cards.";
      list flexibleCard {
        key "position entIndex";
        description
          "Flexible card.";
        leaf position {
          type string {
            length "0..32";
          }
          description
            "Flexible card position.";
        }
        leaf entIndex {
          type uint32;
          description
            "Flexible card index.";
        }
        leaf cardType {
          type devmSubCardType;
          config false;
          mandatory true;
          description
            "Type of a flexible card.";
        }
        leaf cardHardType {
          type devmCardHardType;
          config false;
          mandatory true;
          description
            "Hardware type of a flexible card.";
        }
        leaf portNum {
          type uint32;
          config false;
          description
            "Number of ports on a flexible card.";
        }
        leaf initStatus {
          type devmCardInitStatusType;
          config false;
          description
            "Initialized status of a flexible card.";
        }
        container picCard {
          config false;
          description
            "PIC card.";
          leaf logicStatus {
            type devmCardLogicStatusType;
            config false;
            description
              "Logic loading status.";
          }
          leaf upTime {
            type yang:date-and-time;
            config false;
            description
              "Up time of a flexible card.";
          }
        }
        container cardTdmParam {
          when "not(../cardHardType!='FLEX_4xCPOS_CARD' and ../cardHardType!='FLEX_1xCPOS_CARD' and ../cardHardType!='FLEX_2XCPOS_CARD' and ../cardHardType!='FLEX_8XCPOS_CARD' and ../cardHardType!='FLEX_4XCPOS_CARD' and ../cardHardType!='FLEX_2XCPOS_CARD' and ../cardHardType!='FLEX_8XCPOS_CARD')";
          description
            "CardTdmParam.";
          leaf idleCode {
            type string {
              length "1..2";
              pattern '^\s*[a-fA-F0-9]+$';
            }
            description
              "IdleCode.";
            ext:allowDelete "true";
          }
        }
        container serviceMode {
          description
            "ServiceMode.";
          leaf portrate {
            when "not(../../cardType!='CR2DP4C2HF11' and ../../cardType!='CR5DP4C2HF70' and ../../cardType!='CR2DP2C1HF11' and ../../cardType!='CR5DP2C1HF70')";
            type devmPortRateType;
            must "../../cardType!='CR2DP4C2HF11' and ../../cardType!='CR5DP4C2HF70' and ../../cardType!='CR2DP2C1HF11' and ../../cardType!='CR5DP2C1HF70' or (not(../../cardType!='CR2DP4C2HF11' and ../../cardType!='CR5DP4C2HF70' and ../../cardType!='CR2DP2C1HF11' and ../../cardType!='CR5DP2C1HF70') and (../portrate='155M' or ../portrate='622M') )";
            default "155M";
            description
              "PortRate.";
            ext:allowDelete "true";
          }
          leaf cardBandwidthMode {
            when "not(../../cardType!='CX68LGXF0')";
            type devmcardBandModeType;
            must "../../cardType!='CX68LGXF0' or (not(../../cardType!='CX68LGXF0') and (../cardBandwidthMode='ETH-28X10GF' or ../cardBandwidthMode='ETH-26X10GF-18XGF' or ../cardBandwidthMode='ETH-20X10GF-24XGF') )";
            default "unSupported";
            description
              "Bandwidth Mode.";
            ext:allowDelete "true";
          }
        }
        container cardPanelSlots {
          config false;
          description
            "Card Panel Slots.";
          leaf cardPanelSlots {
            type string {
              length "0..32";
            }
            config false;
            description
              "Card Panel Slots.";
          }
        }
        container queuePriority {
          description
            "MAC Queue Priority Enable.";
          leaf queuePriEnable {
            type devmQueuePriorityType;
            must "../queuePriEnable='notSupport' or (not(../queuePriEnable='notSupport') and (../queuePriEnable='disable' or ../queuePriEnable='enable') )";
            default "enable";
            description
              "MAC Queue Priority Enable.";
            ext:allowDelete "true";
          }
        }
        container cardFrameFormat {
          description
            "CardFrameFormat.";
          leaf frameFormat {
            when "not(../../cardType!='CR5D00A2CF70' and ../../cardType!='CR2D00A2CF10')";
            type devmFrameFormatType;
            must "../../cardType!='CR5D00A2CF70' and ../../cardType!='CR2D00A2CF10' or (not(../../cardType!='CR5D00A2CF70' and ../../cardType!='CR2D00A2CF10') and (../frameFormat='SONET' or ../frameFormat='SDH') )";
            default "SDH";
            description
              "FrameFormat.";
            ext:allowDelete "true";
          }
        }
        container invalidPortInfos {
          config false;
          description
            "Invalid Port.";
          list invalidPortInfo {
            key "position slotId";
            config false;
            description
              "Invalid Port.";
            leaf position {
              type string {
                length "0..32";
              }
              config false;
              description
                "Port position.";
            }
            leaf slotId {
              type string {
                length "0..32";
              }
              config false;
              description
                "SlotID.";
            }
          }
        }
      }
    }
    container cfCards {
      config false;
      description
        "CF cards.";
      list cfCard {
        key "position entSerialNo";
        config false;
        description
          "CF card.";
        leaf position {
          type string {
            length "0..32";
          }
          config false;
          description
            "CF card position.";
        }
        leaf entSerialNo {
          type string {
            length "0..32";
          }
          config false;
          description
            "Number of a CF card.";
        }
        leaf entIndex {
          type uint32;
          config false;
          description
            "CF card index.";
        }
        leaf cardType {
          type devmSubCardType;
          config false;
          description
            "Hard type of a CF card.";
        }
        leaf memorySize {
          type uint32;
          units "M Bytes";
          config false;
          description
            "Memory size of a CF card.";
        }
        leaf memoryUsed {
          type uint32;
          units "M Bytes";
          config false;
          description
            "Memory Used of a CF card.";
        }
        leaf memoryUsage {
          type uint32;
          units %;
          config false;
          description
            "Memory available of a CF card.";
        }
      }
    }
    container ports {
      description
        "Ports.";
      list port {
        key "position";
        description
          "Port.";
        leaf position {
          type string {
            length "0..32";
          }
          description
            "Port position.";
        }
        leaf entIndex {
          type uint32 {
            range "1..4294967295";
          }
          default "1";
          config false;
          description
            "Port index.";
        }
        leaf adminState {
          when "not(../portHardType='ADMCHANNEL' or ../portHardType='ADMLINEPORT')";
          type devmEntityAdminState;
          must "((../adminState='active' or ../adminState='inactive') )";
          description
            "Administration state of a port.";
          ext:allowDelete "true";
        }
        leaf portType {
          type devmPortType;
          config false;
          description
            "Port type (for example, ETH, POS, and OTN).";
        }
        leaf portHardType {
          type devmPortHardType;
          description
            "Hardware type of a port.";
          ext:allowDelete "true";
        }
        leaf loopbackMode {
          when "not(../portHardType='ADMCHANNEL' or ../portHardType='ADMLINEPORT')";
          type devmLoopBackState;
          must "(../cposPort/clock='slave' and (../loopbackMode='noLoopback' or ../loopbackMode='remoteLoopback') ) or (../e1t1Port/clock='master' and (../loopbackMode='noLoopback' or ../loopbackMode='localLoopback') ) or (../e1t1Port/clock='slave' and (../loopbackMode='noLoopback' or ../loopbackMode='remoteLoopback') ) or (../e3t3Port/clock='master' and (../loopbackMode='noLoopback' or ../loopbackMode='localLoopback') ) or (../e3t3Port/clock='slave' and (../loopbackMode='noLoopback' or ../loopbackMode='remoteLoopback') ) or not(../cposPort/clock='slave' or ../e1t1Port/clock='master' or ../e1t1Port/clock='slave' or ../e3t3Port/clock='master' or ../e3t3Port/clock='slave')";
          description
            "Port loopback mode.";
          ext:allowDelete "true";
        }
        leaf portTxEnDelay {
          when "not(../portHardType='ADMCHANNEL' or ../portHardType='ADMLINEPORT' or ../portHardType='EthMGEPort')";
          type uint32 {
            range "0..86400000";
          }
          default "0";
          description
            "Port Tx Enable Delay.";
          ext:allowDelete "false";
        }
        leaf lastUpTime {
          type yang:date-and-time;
          config false;
          description
            "Last up time of a port.";
        }
        leaf lastDownTime {
          type yang:date-and-time;
          config false;
          description
            "Last down time of a port.";
        }
        leaf mediumType {
          type devmEthPortMediumType;
          config false;
          description
            "Port medium type. ";
        }
        leaf opticalIsEquipped {
          type boolean;
          config false;
          description
            "The optical transceiver has been equipped or not.";
        }
        leaf physicalbw {
          type uint64 {
            range "0..10000000000000";
          }
          default "0";
          config false;
          description
            "Port physical bandwitch.";
        }
        leaf portTxReTime {
          type uint32 {
            range "0..86400000";
          }
          default "0";
          config false;
          description
            "Port Tx Remanent Time.";
        }
        container opticalInfo {
          when "not(../portHardType='ADMCHANNEL' or ../portHardType='ADMLINEPORT' or ../portHardType='EthMGEPort')";
          description
            "Information about optical transceivers.";
          leaf vendorName {
            type string {
              length "0..20";
            }
            config false;
            description
              "Name of an optical transceiver Verder.";
          }
          leaf vendorPN {
            type string {
              length "0..20";
            }
            config false;
            description
              "Optical Transceiver Verder PN.";
          }
          leaf transBW {
            type string {
              length "0..16";
            }
            config false;
            description
              "Optical transceiver bandwidth.";
          }
          leaf optTransMode {
            type devmTransMode;
            config false;
            description
              "Optical transceiver transmission mode.";
          }
          leaf opticalPlug {
            type boolean;
            default "true";
            config false;
            description
              "Hot plug.";
          }
          leaf opticalType {
            type devmOpticalType;
            config false;
            description
              "Optical type.";
          }
          leaf opticalFiberType {
            type devmOpticalFiberType;
            config false;
            description
              "Optical fiber type.";
          }
          leaf waveLength {
            type string {
              length "0..128";
            }
            config false;
            description
              "Wave length.";
          }
          leaf transDistance {
            type string {
              length "0..32";
            }
            config false;
            description
              "Transmit distance.";
          }
          leaf txPower {
            type string {
              length "0..64";
            }
            config false;
            description
              "Transmit power.";
          }
          leaf rxPower {
            type string {
              length "0..64";
            }
            config false;
            description
              "Receive power.";
          }
          leaf optRxHighWarn {
            type string {
              length "0..64";
            }
            config false;
            description
              "Receive high warning power.";
          }
          leaf optRxLowWarn {
            type string {
              length "0..64";
            }
            config false;
            description
              "Receive low warning power.";
          }
          leaf optTxHighWarn {
            type string {
              length "0..64";
            }
            config false;
            description
              "Transmit high warning power.";
          }
          leaf optTxLowWarn {
            type string {
              length "0..64";
            }
            config false;
            description
              "Transmit low warning power.";
          }
          leaf optRxHighAlarm {
            type string {
              length "0..64";
            }
            config false;
            description
              "Receive high alarm power.";
          }
          leaf optRxLowAlarm {
            type string {
              length "0..64";
            }
            config false;
            description
              "Receive high alarm power.";
          }
          leaf optTxHighAlarm {
            type string {
              length "0..64";
            }
            config false;
            description
              "Transmit high alarm power.";
          }
          leaf optTxLowAlarm {
            type string {
              length "0..64";
            }
            config false;
            description
              "Transmit low alarm power.";
          }
          leaf optRxHighWarnEn {
            when "not(../../mediumType='copper')";
            type boolean;
            default "true";
            description
              "Receive optical power high warning.";
            ext:allowDelete "true";
          }
          leaf optRxLowWarnEn {
            when "not(../../mediumType='copper')";
            type boolean;
            default "true";
            description
              "Receive optical power low warning.";
            ext:allowDelete "true";
          }
          leaf optTxHighWarnEn {
            when "not(../../mediumType='copper')";
            type boolean;
            default "true";
            description
              "Transmit optical power high warning.";
            ext:allowDelete "true";
          }
          leaf optTxLowWarnEn {
            when "not(../../mediumType='copper')";
            type boolean;
            default "true";
            description
              "Transmit optical power low warning.";
            ext:allowDelete "true";
          }
          leaf opticalTunableType {
            type devmOpticalTunableType;
            default "notSupported";
            config false;
            description
              "0ptical module tunable type.";
          }
          leaf waveLengthChannelNum {
            when "not(../../portType!='GE')";
            type devmTunableWaveLengthType;
            default "No-configurable";
            description
              "Tunable optical module wave length.";
          }
          leaf chromaticDispersion {
            type string {
              length "0..32";
            }
            config false;
            description
              "Chromatic dispersion.";
          }
          leaf polarizationModeDispersion {
            type string {
              length "0..32";
            }
            config false;
            description
              "Polarization mode dispersion.";
          }
          leaf directionType {
            type devmOpticalDirectionType;
            default "notSupported";
            config false;
            description
              "0ptical module direction type.";
          }
          leaf optSignalDqpsk {
            type uint32 {
              range "1..8";
            }
            default "1";
            description
              "Differential quadrature phase shift keying.";
            ext:allowDelete "true";
          }
          leaf optVoltHWarnEn {
            when "not(../../mediumType='copper')";
            type boolean;
            default "true";
            description
              "Optical module voltage high warning.";
            ext:allowDelete "true";
          }
          leaf optVoltLWarnEn {
            when "not(../../mediumType='copper')";
            type boolean;
            default "true";
            description
              "Optical module voltage low warning.";
            ext:allowDelete "true";
          }
          leaf optTotalRxPower {
            type string {
              length "0..64";
            }
            config false;
            description
              "Total Receive Power(dBm).";
          }
          leaf optTotalRxHighWarn {
            type string {
              length "0..64";
            }
            config false;
            description
              "Total Receive High Warning Power(dBm).";
          }
          leaf optTotalRxLowWarn {
            type string {
              length "0..64";
            }
            config false;
            description
              "Total Receive Low Warning Power(dBm).";
          }
          leaf optTotalRxHighALarm {
            type string {
              length "0..64";
            }
            config false;
            description
              "Total Receive High Alarm Power(dBm).";
          }
          leaf optTotalRxLowALarm {
            type string {
              length "0..64";
            }
            config false;
            description
              "Total Receive Low Alarm Power(dBm).";
          }
          leaf optSignalDqpskTx {
            type uint32 {
              range "1..8";
            }
            default "1";
            description
              "Differential quadrature phase shift keying transmit value.";
            ext:allowDelete "true";
          }
          leaf optSignalDqpskRx {
            type uint32 {
              range "1..8";
            }
            default "1";
            description
              "Differential quadrature phase shift keying receive value.";
            ext:allowDelete "true";
          }
        }
        container ethernetPort {
          when "not(../portHardType='ADMCHANNEL' or ../portHardType='ADMLINEPORT' or ../portHardType='AtmPort' or ../portHardType='CposPort' or ../portHardType='E1Port' or ../portHardType='E3Port' or ../portHardType='PosPort')";
          description
            "Ethernet port.";
          leaf flowctl {
            when "not(../../portHardType='EthMGEPort')";
            type devmFlowCtlType;
            default "defaultConfig";
            description
              "Flow control method of an Ethernet port.";
            ext:allowDelete "true";
          }
          leaf negotiation {
            when "not(../../portHardType='EthMGEPort' or ../portMode='10G')";
            type devmNegotiationType;
            default "enabled";
            description
              "Auto negotiation on an Ethernet port.";
            ext:allowDelete "true";
          }
          leaf speed {
            when "not(../portMode='10G')";
            type devmEthSpeedType;
            default "auto";
            description
              "Speed of an Ethernet port.";
            ext:allowDelete "true";
          }
          leaf duplex {
            when "not(../portMode='10G')";
            type devmDuplex;
            must "not(../portMode='1G') or (../portMode='1G' and (../duplex='full' or ../duplex='auto') )";
            description
              "Duplex type of an Ethernet port.";
            ext:allowDelete "true";
          }
          leaf downHoldTime {
            when "not(../../portHardType='EthMGEPort') or ../transMode!='wanMode' and ../transMode!='otnMode'";
            type uint32 {
              range "0..86400000";
            }
            default "0";
            description
              "down hold time.";
            ext:allowDelete "true";
          }
          leaf upHoldTime {
            when "not(../../portHardType='EthMGEPort') or ../transMode!='wanMode' and ../transMode!='otnMode'";
            type uint32 {
              range "0..86400000";
            }
            default "200";
            description
              "up hold time.";
            ext:allowDelete "true";
          }
          leaf transMode {
            when "not(../../portHardType='EthMGEPort') or ../portMode='10G'";
            type devmPortLanWanModeType;
            must "not(../portMode='10G') or (../portMode='10G' and (../transMode='lanMode' or ../transMode='wanMode') )";
            description
              "transmit mode of an Ethernet port.";
            ext:allowDelete "true";
          }
          leaf gfMediaType {
            when "not(../../portHardType='EthMGEPort' or ../portMode='10G') or ../portMode='1G'";
            type devmGfMediaType;
            default "auto";
            description
              "Medium type on an Ethernet GF port.";
            ext:allowDelete "true";
          }
          leaf proMode {
            when "not(../../portHardType!='EthMGEPort')";
            type devmPortPromodeType;
            description
              "Promiscuous of an Ethernet MGE port.";
            ext:allowDelete "true";
          }
          leaf holdUp {
            when "not(../../portHardType='EthMGEPort')";
            type devmHoldupType;
            default "disabled";
            description
              "Whether the hold-up function is configured on a Ethernet port. ";
            ext:allowDelete "true";
          }
          leaf bitError {
            when "../transMode='otnMode'";
            type devmBitErrorType;
            must "not(../transMode='otnMode') or (../transMode='otnMode' and (../bitError='crc' or ../bitError='prefec') )";
            default "crc";
            description
              "bit error type. ";
            ext:allowDelete "true";
          }
          leaf triggerTime {
            when "../../portHardType='EthLANPort' and ../bitError='prefec'";
            type uint32 {
              range "1..100";
            }
            default "30";
            description
              "prefec error detecting cycle. ";
            ext:allowDelete "true";
          }
          leaf triggerTimeType {
            when "../../portHardType='EthLANPort' and ../bitError='prefec'";
            type devmTriggerTimeType;
            must "../triggerTime>4 or (not(../triggerTime>4) and (../triggerTimeType='second' or ../triggerTimeType='200ms') ) or (../../portHardType='EthLANPort' and ../bitError='prefec' and (../triggerTimeType='second' or ../triggerTimeType='200ms') ) or not(../../portHardType='EthLANPort' and ../bitError='prefec')";
            description
              "prefec error detecting cycle type. ";
            ext:allowDelete "true";
          }
          leaf attenuation {
            when "not(../bitError='No-configurable') or ../txPowerCfgType='attenuation'";
            type uint32 {
              range "0..200";
            }
            default "0";
            description
              "Optical attenuation(0.1dB).";
            ext:allowDelete "true";
          }
          leaf txPowerCfgType {
            when "not(../../portHardType='EthMGEPort' or ../../portType)";
            type devmtxPowerCfgType;
            must "not(not(../../portType)) or (not(../../portType) and (../txPowerCfgType='attenuation' or ../txPowerCfgType='txPowerTargetValue' or ../txPowerCfgType='unsupport') )";
            default "txPowerTargetValue";
            description
              "Optical power cfg type.";
            ext:allowDelete "true";
          }
          leaf txPowerTargetValue {
            when "../txPowerCfgType='txPowerTargetValue'";
            type int32 {
              range "-180..0";
            }
            default "-5";
            description
              "Optical power target value(0.1dB).";
            ext:allowDelete "true";
          }
          leaf negoMode {
            when "not(../../portHardType='EthMGEPort') or ../../portHardType='EthGEPort'";
            type devmnegoModeType;
            default "NA";
            description
              "Auto Negotiation Mode.";
            ext:allowDelete "true";
          }
          leaf lfStatus {
            type devmPortFaultType;
            config false;
            description
              "Local fault.";
          }
          leaf rfStatus {
            type devmPortFaultType;
            config false;
            description
              "Remote fault.";
          }
          leaf txipg {
            when "not(../../portHardType='EthMGEPort')";
            type devmTxIpgType;
            default "shrink";
            description
              "Inter-packet Gap.";
            ext:allowDelete "true";
          }
          leaf portMode {
            when "not(../../portHardType='EthMGEPort')";
            type devmPortModeType;
            description
              "Switch GE/10GE.";
            ext:allowDelete "true";
          }
          leaf fecMode {
            when "not(../../portHardType='EthMGEPort' or ../transMode!='otnMode')";
            type devmFecModeType;
            default "standard";
            description
              "fecMode.";
            ext:allowDelete "true";
          }
          leaf ethFecMode {
            type devmEthFecmodeType;
            default "none";
            description
              "Eth Fec Mode.";
            ext:allowDelete "true";
          }
          container ethWANAttr {
            when "not(../../portHardType!='EthWANPort' and ../transMode!='wanMode' or ../../portHardType='EthMGEPort')";
            description
              "Ethernet port attributes.";
            leaf frameFormat {
              type devmFrameFormatType;
              default "SDH";
              description
                "Frame format of a WAN port.";
              ext:allowDelete "true";
            }
            leaf j0Mode {
              type devmWANSdhFlagModeType;
              default "16byte";
              description
                "j0 mode on an Ethernet WAN port.";
              ext:allowDelete "true";
            }
            leaf j0Value {
              when "not(../j0Mode='16byte' or ../j0Mode='64byte-or-null-mode') or ../j0Mode='1byte'";
              type uint32 {
                range "0..255";
              }
              description
                "Vaule of j0Mode on an Ethernet WAN port.";
              ext:allowDelete "true";
            }
            leaf j0Trace {
              when "not(../j0Mode='1byte') or ../j0Mode='16byte' or ../j0Mode='64byte-or-null-mode'";
              type string {
                length "0..64";
              }
              default "NA";
              description
                "Description of the j0 mode on an Ethernet WAN port.";
            }
            leaf j1Mode {
              type devmWANSdhFlagModeType;
              default "16byte";
              description
                "j1 mode on an Ethernet WAN port on an Ethernet WAN port.";
              ext:allowDelete "true";
            }
            leaf j1Value {
              when "not(../j1Mode='16byte' or ../j1Mode='64byte-or-null-mode') or ../j1Mode='1byte'";
              type uint32 {
                range "0..255";
              }
              description
                "Value of j1Mode on an Ethernet WAN port.";
              ext:allowDelete "true";
            }
            leaf j1Trace {
              when "not(../j1Mode='1byte') or ../j1Mode='16byte' or ../j1Mode='64byte-or-null-mode'";
              type string {
                length "0..64";
              }
              default "NA";
              description
                "Description of the j1 mode on an Ethernet WAN port.";
            }
            leaf c2 {
              type uint32 {
                range "0..255";
              }
              default "26";
              description
                "C2 mode on an Ethernet WAN port.";
              ext:allowDelete "true";
            }
            leaf clock {
              type devmSdhClockType;
              default "master";
              description
                "Active/standby clock on an Ethernet WAN port. ";
              ext:allowDelete "true";
            }
            leaf scramble {
              type devmScrambleType;
              default "enabled";
              description
                "Whether the scrambling function is configured on an Ethernet WAN port. ";
              ext:allowDelete "true";
            }
            leaf rxj0Mode {
              type devmSdhFlagModeType;
              config false;
              description
                "rxj0Mode on an Ethernet WAN port.";
            }
            leaf rxj0Value {
              type uint32 {
                range "0..127";
              }
              config false;
              description
                "Value of rxj0mode on an Ethernet WAN port.";
            }
            leaf rxj0Trace {
              type string {
                length "0..64";
              }
              config false;
              description
                "rxj0Trace on an Ethernet WAN port.";
            }
            leaf rxj1Mode {
              type devmSdhFlagModeType;
              config false;
              description
                "rxj1Mode on an Ethernet WAN port.";
            }
            leaf rxj1Value {
              type uint32 {
                range "0..127";
              }
              config false;
              description
                "Value of rxj1mode on an Ethernet WAN port.";
            }
            leaf rxj1Trace {
              type string {
                length "0..64";
              }
              config false;
              description
                "rxj1Trace on an Ethernet WAN port.";
            }
            leaf rxc2 {
              type uint32 {
                range "0..255";
              }
              config false;
              description
                "rxC2 on an Ethernet WAN port.";
            }
          }
        }
        container posPort {
          when "not(../ethernetPort/flowctl or ../portHardType='ADMCHANNEL' or ../portHardType='ADMLINEPORT' or ../portHardType='AtmPort' or ../portHardType='CposPort' or ../portHardType='E1Port' or ../portHardType='E3Port' or ../portHardType='EthMGEPort') or ../portHardType='PosPort'";
          description
            "Pos port.";
          leaf frameFormat {
            type devmFrameFormatType;
            default "SDH";
            description
              "Frame format of a POS port.";
            ext:allowDelete "true";
          }
          leaf scramble {
            type devmScrambleType;
            default "enabled";
            description
              "Whether the scrambling function is configured on a POS port. ";
            ext:allowDelete "true";
          }
          leaf clock {
            type devmSdhClockType;
            default "master";
            description
              "Active/standby clock of a POS port.";
            ext:allowDelete "true";
          }
          leaf j0Mode {
            type devmSdhFlagModeType;
            default "16byte";
            description
              "j0 mode of a POS port.";
            ext:allowDelete "true";
          }
          leaf j0Value {
            when "not(../j0Mode='16byte' or ../j0Mode='64byte-or-null-mode' or ../j0Mode='peer') or ../j0Mode='1byte'";
            type uint32 {
              range "0..127";
            }
            description
              "Value of j0Mode of a POS port.";
            ext:allowDelete "true";
          }
          leaf j0Trace {
            when "not(../j0Mode='1byte' or ../j0Mode='peer') or ../j0Mode='16byte' or ../j0Mode='64byte-or-null-mode'";
            type string {
              length "0..64";
            }
            default "NA";
            description
              "j0mode trace of a POS port.";
          }
          leaf j1Mode {
            type devmSdhFlagModeType;
            default "16byte";
            description
              "j1Mode of a POS port.";
            ext:allowDelete "true";
          }
          leaf j1Value {
            when "not(../j1Mode='16byte' or ../j1Mode='64byte-or-null-mode' or ../j1Mode='peer') or ../j1Mode='1byte'";
            type uint32 {
              range "0..127";
            }
            description
              "Value of j1Mode a POS port.";
            ext:allowDelete "true";
          }
          leaf j1Trace {
            when "not(../j1Mode='1byte' or ../j1Mode='peer') or ../j1Mode='16byte' or ../j1Mode='64byte-or-null-mode'";
            type string {
              length "0..64";
            }
            default "NA";
            description
              "j1Trace of a POS port";
          }
          leaf crc {
            type devmSdhCRCType;
            default "32";
            description
              "CRC mode of a POS port, which can be 32 or 64 bytes.";
            ext:allowDelete "true";
          }
          leaf c2 {
            type uint32 {
              range "0..255";
            }
            default "22";
            description
              "C2 of a POS port.";
            ext:allowDelete "true";
          }
          leaf rxj0Mode {
            type devmSdhFlagModeType;
            config false;
            description
              "rxj0Mode of a POS port.";
          }
          leaf rxj0Value {
            type uint32 {
              range "0..127";
            }
            config false;
            description
              "Value of rxj0Mode of a POS port.";
          }
          leaf rxj0Trace {
            type string {
              length "0..64";
            }
            config false;
            description
              "rxj0Trace of a POS port";
          }
          leaf rxj1Mode {
            type devmSdhFlagModeType;
            config false;
            description
              "rxj1Mode of a POS port";
          }
          leaf rxj1Value {
            type uint32 {
              range "0..127";
            }
            config false;
            description
              "Value of rxj1Mode  of a POS port.";
          }
          leaf rxj1Trace {
            type string {
              length "0..64";
            }
            config false;
            description
              "rxj1Trace  of a POS port.";
          }
          leaf rxc2 {
            type uint32 {
              range "0..255";
            }
            config false;
            description
              "rxC2 of a POS port.";
          }
          leaf holdUp {
            type devmHoldupType;
            default "disabled";
            description
              "Whether the hold-up function is configured on a POS port. ";
            ext:allowDelete "true";
          }
        }
        container cposPort {
          when "not(../ethernetPort/flowctl or ../portHardType='ADMCHANNEL' or ../portHardType='ADMLINEPORT' or ../portHardType='AtmPort' or ../portHardType='E1Port' or ../portHardType='E3Port' or ../portHardType='EthMGEPort' or ../portHardType='PosPort') or ../portHardType='CposPort'";
          description
            "Cpos port.";
          leaf clock {
            type devmcposclockmodeType;
            default "master";
            description
              "Clock mode.";
            ext:allowDelete "true";
          }
          leaf mappingMode {
            type devmcposMapModeType;
            default "h-mode";
            description
              "Mapping mode.";
            ext:allowDelete "true";
          }
          leaf frameFormat {
            type devmcposFrameFormatType;
            must "not(../../portType='Cpos' and ../../portHardType='CposPort') or (../../portType='Cpos' and ../../portHardType='CposPort' and (../frameFormat='sdh') )";
            default "sdh";
            description
              "Cpos port frame format.";
            ext:allowDelete "true";
          }
          leaf multiplex {
            type devmcposMultiplexType;
            must "not(../../portType='Cpos' and ../../portHardType='CposPort') or (../../portType='Cpos' and ../../portHardType='CposPort' and (../multiplex='au-4') )";
            default "au-4";
            description
              "Multiplex mode.";
            ext:allowDelete "true";
          }
          leaf j0Mode {
            type devmcposFrameFormatType;
            must "not(../../portType='Cpos' and ../../portHardType='CposPort') or (../../portType='Cpos' and ../../portHardType='CposPort' and (../j0Mode='sdh') )";
            default "sdh";
            description
              "j0Mode.";
            ext:allowDelete "true";
          }
          leaf j0Value {
            type string {
              length "1..15";
            }
            default "NetEngine";
            description
              "j0Value.";
          }
          leaf j1Mode {
            type devmCPOSSdhFlagModeType;
            default "16byte";
            description
              "j1Mode.";
            ext:allowDelete "true";
          }
          leaf j1Value {
            when "not(../j1Mode='16byte' or ../j1Mode='64byte') or ../j1Mode='1byte'";
            type uint32 {
              range "0..127";
            }
            description
              "j1Value.";
            ext:allowDelete "true";
          }
          leaf j1Trace {
            when "not(../j1Mode='1byte') or ../j1Mode='16byte' or ../j1Mode='64byte'";
            type string {
              length "1..62";
            }
            default "NetEngine";
            description
              "j1Trace.";
          }
          leaf c2Value {
            type uint32 {
              range "0..255";
            }
            default "2";
            description
              "c2Value.";
            ext:allowDelete "true";
          }
          leaf rxj0Value {
            type string {
              length "0..15";
            }
            config false;
            description
              "rxj0Value.";
          }
          leaf rxj1Value {
            type uint32 {
              range "0..127";
            }
            config false;
            description
              "rxj1Value.";
          }
          leaf rxj1Trace {
            type string {
              length "0..64";
            }
            config false;
            description
              "rxj1Trace.";
          }
          leaf rxc2Value {
            type uint32 {
              range "0..255";
            }
            config false;
            description
              "rxc2Value.";
          }
          leaf holdUp {
            type devmHoldupType;
            default "disabled";
            description
              "Whether the hold-up function is configured on a CPOS port. ";
            ext:allowDelete "true";
          }
          leaf lbHoldTime {
            when "../../loopbackMode!='noLoopback' and ../../portHardType='CposPort'";
            type uint32 {
              range "0..43200";
            }
            default "0";
            description
              "Cpos Port Loopback auto-clear period.";
            ext:allowDelete "true";
          }
          leaf hpMappingMode {
            when "../../portType='Cpos'";
            type devmcposvc4vc12modeType;
            default "VC12";
            description
              "HpMappingMode.";
            ext:allowDelete "true";
          }
          container e1t1s {
            description
              "E1T1 port attributes.";
            list e1t1 {
              when "not(../../hpMappingMode='VC4')";
              key "e1t1-Number";
              max-elements  "63";
              description
                "E1T1 port attribute.";
              leaf e1t1-Number {
                type uint32 {
                  range "1..63";
                }
                description
                  "E1T1 number.";
              }
              leaf workMode {
                type devmE1T1WorkModeType;
                default "framed";
                description
                  "E1T1 Work mode.";
                ext:allowDelete "true";
              }
              leaf clock {
                type devmCposE1ClockModeType;
                default "master";
                description
                  "Clock mode.";
                ext:allowDelete "true";
              }
              leaf clockValue {
                when "not(../clock='master' or ../clock='slave') or ../clock='master-domain' or ../clock='recovery-domain'";
                type uint32 {
                  range "1..32";
                }
                default "1";
                description
                  "Clock value.";
                ext:allowDelete "true";
              }
              leaf frameformat {
                when "not(../workMode='unframed') or ../workMode='framed'";
                type devmCposE1FrameFormatType;
                default "no-crc4";
                description
                  "Frame format.";
                ext:allowDelete "true";
              }
              leaf loopback {
                type devmCposE1LoopbackType;
                must "(../clock='master' and (../loopback='none' or ../loopback='local') ) or (../clock='slave' and (../loopback='none' or ../loopback='remote') ) or not(../clock='master' or ../clock='slave')";
                default "none";
                description
                  "Loopback mode.";
                ext:allowDelete "true";
              }
              leaf j2Trace {
                type string {
                  length "1..15";
                }
                default "NetEngine";
                description
                  "j2Trace.";
              }
              leaf rxj2Trace {
                type string {
                  length "1..15";
                }
                config false;
                description
                  "rxj2Trace.";
              }
              leaf v5Trace {
                type uint32 {
                  range "0..7";
                }
                default "0";
                description
                  "v5Trace.";
              }
              leaf autoClrPeriod {
                when "not(../loopback='none')";
                type uint32 {
                  range "0..43200";
                }
                default "0";
                description
                  "Loopback auto-clear period.";
                ext:allowDelete "true";
              }
              container channel-sets {
                description
                  "Channel-sets.";
                list channel-set {
                  when "not(../../workMode='unframed') or ../../workMode='framed'";
                  key "set-Number timeslot-list";
                  max-elements  "30";
                  description
                    "Channel-sets.";
                  leaf set-Number {
                    type uint32 {
                      range "0..30";
                    }
                    description
                      "Set number.";
                  }
                  leaf timeslot-list {
                    type pub-type:devmTimeslotListType {
                      length "1..61";
                    }
                    description
                      "Timeslot list.";
                  }
                }
              }
            }
          }
        }
        container e1t1Port {
          when "not(../ethernetPort/flowctl or ../portHardType='ADMCHANNEL' or ../portHardType='ADMLINEPORT' or ../portHardType='AtmPort' or ../portHardType='CposPort' or ../portHardType='E3Port' or ../portHardType='EthMGEPort' or ../portHardType='PosPort') or ../portHardType='E1Port'";
          description
            "E1T1 port.";
          leaf workMode {
            type devmE1T1WorkModeType;
            default "framed";
            description
              "E1T1 Work mode.";
            ext:allowDelete "true";
          }
          leaf frameFormat {
            when "not(../workMode='unframed') or ../workMode='framed'";
            type devmE1CRCType;
            default "no-crc4";
            description
              "E1T1 port frame format.";
            ext:allowDelete "true";
          }
          leaf clock {
            type devmE1ClockType;
            default "master";
            description
              "Clock mode.";
            ext:allowDelete "true";
          }
          leaf code {
            type devmE1CodeType;
            default "hdb3";
            description
              "Code.";
            ext:allowDelete "true";
          }
          leaf lbHoldTime {
            when "../../loopbackMode!='noLoopback' and ../../portHardType='E1Port'";
            type uint32 {
              range "0..43200";
            }
            default "0";
            description
              "E1T1 Port Loopback auto-clear period.";
            ext:allowDelete "true";
          }
          container channel-sets {
            description
              "Channel-sets.";
            list channel-set {
              when "not(../../workMode='unframed') or ../../workMode='framed'";
              key "set-Number timeslot-list";
              max-elements  "30";
              description
                "Channel-sets.";
              leaf set-Number {
                type uint32 {
                  range "0..30";
                }
                description
                  "Set number.";
              }
              leaf timeslot-list {
                type pub-type:devmTimeslotListType {
                  length "1..61";
                }
                description
                  "Timeslot list.";
              }
            }
          }
        }
        container e3t3Port {
          when "not(../portHardType='AtmPort' or ../portHardType='CposPort' or ../portHardType='E1Port' or ../portHardType='EthMGEPort') or ../portHardType='E3Port'";
          description
            "E3T3 port.";
          leaf workMode {
            type devmE1T1WorkModeType;
            default "framed";
            description
              "E3T3 Work mode.";
            ext:allowDelete "true";
          }
          leaf frameFormat {
            type e3t3FrameFormat;
            config false;
            description
              "E3T3 port frame format.";
          }
          leaf ifFramed {
            when "not(../../portType!='E3' and ../../portHardType!='E3Port' or ../workMode='unframed')";
            type boolean;
            default "false";
            description
              "If Create Framed Serial Port.";
            ext:allowDelete "true";
          }
          leaf e3t3Flag {
            type e3t3FlagType;
            config false;
            description
              "E3T3 service mode.";
          }
          leaf clock {
            type devmE1ClockType;
            default "master";
            description
              "Clock mode.";
            ext:allowDelete "true";
          }
          container e1t1s {
            description
              "E1T1 port attributes.";
            list e1t1 {
              key "e1t1-Number";
              max-elements  "63";
              description
                "E1T1 port attribute.";
              leaf e1t1-Number {
                type uint32 {
                  range "1..63";
                }
                description
                  "E1T1 number.";
              }
              leaf workMode {
                type devmE1T1WorkModeType;
                default "framed";
                description
                  "E1T1 Work mode.";
                ext:allowDelete "true";
              }
              leaf clock {
                type devmCposE1ClockModeType;
                default "master";
                description
                  "Clock mode.";
                ext:allowDelete "true";
              }
              leaf clockValue {
                type uint32 {
                  range "1..32";
                }
                default "1";
                description
                  "Clock value.";
                ext:allowDelete "true";
              }
              leaf frameformat {
                type devmCposE1FrameFormatType;
                default "no-crc4";
                description
                  "Frame format.";
                ext:allowDelete "true";
              }
              leaf loopback {
                type devmCposE1LoopbackType;
                default "none";
                description
                  "Loopback mode.";
                ext:allowDelete "true";
              }
              leaf j2Trace {
                type string {
                  length "1..15";
                }
                default "NetEngine";
                description
                  "j2Trace.";
              }
              leaf rxj2Trace {
                type string {
                  length "1..15";
                }
                config false;
                description
                  "rxj2Trace.";
              }
              leaf v5Trace {
                type uint32 {
                  range "0..7";
                }
                default "0";
                description
                  "v5Trace.";
              }
              leaf autoClrPeriod {
                type uint32 {
                  range "0..43200";
                }
                default "0";
                description
                  "Loopback auto-clear period.";
                ext:allowDelete "true";
              }
              container channel-sets {
                description
                  "Channel-sets.";
                list channel-set {
                  key "set-Number timeslot-list";
                  max-elements  "30";
                  description
                    "Channel-sets.";
                  leaf set-Number {
                    type uint32 {
                      range "0..30";
                    }
                    description
                      "Set number.";
                  }
                  leaf timeslot-list {
                    type pub-type:devmTimeslotListType {
                      length "1..61";
                    }
                    description
                      "Timeslot list.";
                  }
                }
              }
            }
          }
        }
        container portAlarmInfo {
          when "not(../portHardType='ADMCHANNEL' or ../portHardType='ADMLINEPORT' or ../portHardType='CposPort' or ../portHardType='E1Port' or ../portHardType='E3Port' or ../portHardType='EthMGEPort')";
          description
            "Port alarm information.";
          leaf crcEnabledDown {
            when "not(../../portHardType='AtmPort')";
            type boolean;
            default "false";
            description
              "CRC error enable eown.";
            ext:allowDelete "true";
          }
          leaf crcErrorHighThreshold {
            when "not(../../portHardType='AtmPort') or ../crcPerAlmEn!='true' and ../crcMfeAlmEn!='true' and ../crcMfsAlmEn!='true' and ../linkQAlmEn!='true' and ../../portHardType!='AtmPort'";
            type uint32 {
              range "1..4294967295";
            }
            units "number of invalid packets";
            default "1000";
            description
              "CRC error high threshold.";
            ext:allowDelete "true";
          }
          leaf crcErrorLowThreshold {
            when "not(../../portHardType='AtmPort') or ../crcPerAlmEn!='true' and ../crcMfeAlmEn!='true' and ../crcMfsAlmEn!='true' and ../linkQAlmEn!='true' and ../../portHardType!='AtmPort'";
            type uint32 {
              range "1..4294967295";
            }
            units "number of invalid packets";
            default "100";
            description
              "CRC error low threshold.";
            ext:allowDelete "true";
          }
          leaf crcErrorInterval {
            when "not(../../portHardType='AtmPort') or ../crcPerAlmEn!='true' and ../crcMfeAlmEn!='true' and ../crcMfsAlmEn!='true' and ../linkQAlmEn!='true' and ../../portHardType!='AtmPort'";
            type uint32 {
              range "1..65535";
            }
            units s;
            default "10";
            description
              "CRC error interval.";
            ext:allowDelete "true";
          }
          leaf crcErrorPercentAlmThr {
            when "not(../../portHardType='AtmPort') or ../crcPerAlmEn!='true' and ../crcMfeAlmEn!='true' and ../crcMfsAlmEn!='true' and ../linkQAlmEn!='true' and ../../portHardType!='AtmPort'";
            type uint32 {
              range "0..100";
            }
            units percentage;
            default "0";
            description
              "crcErrorPercentAlmThr.";
            ext:allowDelete "true";
          }
          leaf inputEnabledDown {
            when "not(../../portHardType='AtmPort')";
            type boolean;
            default "false";
            description
              "Input error enable eown.";
            ext:allowDelete "true";
          }
          leaf inputErrorHighThreshold {
            when "not(../../portHardType='AtmPort')";
            type uint32 {
              range "1..4294967295";
            }
            units "number of invalid packets";
            default "1000";
            description
              "Input error high threshold.";
            ext:allowDelete "true";
          }
          leaf inputErrorLowThreshold {
            when "not(../../portHardType='AtmPort')";
            type uint32 {
              range "1..4294967295";
            }
            units "number of invalid packets";
            default "100";
            description
              "Input error low threshold.";
            ext:allowDelete "true";
          }
          leaf inputErrorInterval {
            when "not(../../portHardType='AtmPort')";
            type uint32 {
              range "1..65535";
            }
            units s;
            default "10";
            description
              "Input error interval.";
            ext:allowDelete "true";
          }
          leaf outputEnabledDown {
            when "not(../../portHardType='AtmPort')";
            type boolean;
            default "false";
            description
              "Output error enable eown.";
            ext:allowDelete "true";
          }
          leaf outputErrorHighThreshold {
            when "not(../../portHardType='AtmPort')";
            type uint32 {
              range "1..4294967295";
            }
            units "number of invalid packets";
            default "1000";
            description
              "Output error high threshold.";
            ext:allowDelete "true";
          }
          leaf outputErrorLowThreshold {
            when "not(../../portHardType='AtmPort')";
            type uint32 {
              range "1..4294967295";
            }
            units "number of invalid packets";
            default "100";
            description
              "Output error low threshold.";
            ext:allowDelete "true";
          }
          leaf outputErrorInterval {
            when "not(../../portHardType='AtmPort')";
            type uint32 {
              range "1..65535";
            }
            units s;
            default "10";
            description
              "Output error interval.";
            ext:allowDelete "true";
          }
          leaf crcPerAlmEn {
            when "not(../../portHardType='AtmPort' or ../crcMfeAlmEn='true' or ../crcMfsAlmEn='true')";
            type boolean;
            default "false";
            description
              "Enalbe or disable the crc PER alarm.";
            ext:allowDelete "true";
          }
          leaf crcPerAlmThrCoefficient {
            when "not(../../portHardType='AtmPort') or ../crcPerAlmEn='true'";
            type uint32 {
              range "1..9";
            }
            mandatory true;
            description
              "Packet error ratio coefficient (x of xE-y). The range is 1 to 9. ";
            ext:allowDelete "true";
          }
          leaf crcPerAlmThrPower {
            when "not(../../portHardType='AtmPort') or ../crcPerAlmEn='true'";
            type uint32 {
              range "1..5";
            }
            mandatory true;
            description
              "Packet error ratio exponent (y of xE-y). The range is 1 to 5.";
            ext:allowDelete "true";
          }
          leaf crcPerRsumThrCoefficient {
            when "not(../../portHardType='AtmPort') or ../crcPerAlmEn='true' or ../crcPerAlmThrCoefficient and ../crcPerAlmThrCoefficient!=0 and ../crcPerAlmThrPower and ../crcPerAlmThrPower!=0";
            type uint32 {
              range "1..9";
            }
            mandatory true;
            description
              "Packet error ratio coefficient (x of xE-y). The range is 1 to 9. ";
            ext:allowDelete "true";
          }
          leaf crcPerRsumThrPower {
            when "not(../../portHardType='AtmPort') or ../crcPerAlmEn='true' or ../crcPerAlmThrCoefficient and ../crcPerAlmThrCoefficient!=0 and ../crcPerAlmThrPower and ../crcPerAlmThrPower!=0";
            type uint32 {
              range "1..6";
            }
            mandatory true;
            description
              "For resume-threshold: Packet error ratio exponent (y of xE-y). The range is 1 to 6.";
            ext:allowDelete "true";
          }
          leaf crcPerSampWinFactor {
            when "not(../../portHardType='AtmPort') or ../crcPerAlmEn='true'";
            type uint32 {
              range "10..100";
            }
            mandatory true;
            description
              "Sample window factor, default is 50.";
            ext:allowDelete "true";
          }
          leaf crcPerChildWinMaxNum {
            when "not(../../portHardType='AtmPort') or ../crcPerAlmEn='true'";
            type uint32 {
              range "10..100";
            }
            mandatory true;
            description
              "Maximum number of child windows, default is 50.";
            ext:allowDelete "true";
          }
          leaf crcPerChildWinAlarmNum {
            when "not(../../portHardType='AtmPort') or ../crcPerAlmEn='true'";
            type uint32 {
              range "1..100";
            }
            mandatory true;
            description
              "Minimal number of child windows for alarm generating, default is 5.";
            ext:allowDelete "true";
          }
          leaf crcPerChildWinResumeNum {
            when "not(../../portHardType='AtmPort') or ../crcPerAlmEn='true'";
            type uint32 {
              range "1..100";
            }
            mandatory true;
            description
              "Minimal number of child windows for alarm resuming, default is 30.";
            ext:allowDelete "true";
          }
          leaf crcAlgRealtimeFactor {
            when "not(../../portHardType='AtmPort') or ../crcPerAlmEn='true'";
            type uint32 {
              range "0..10";
            }
            mandatory true;
            description
              "crcAlgRealtimeFactor.";
            ext:allowDelete "true";
          }
          leaf crcShutDownEn {
            when "not(../../portHardType='AtmPort') or ../crcPerAlmEn!='true' and ../crcMfeAlmEn!='true' and ../crcMfsAlmEn!='true' and ../linkQAlmEn!='true' and ../../portHardType!='AtmPort'";
            type boolean;
            default "false";
            description
              "crc ShutDown.";
            ext:allowDelete "true";
          }
          leaf crcPerAlmLspEn {
            when "not(../../portHardType='AtmPort') or ../crcPerAlmEn='true'";
            type boolean;
            must "not(../crcPerAlmSecEn='true') or (../crcPerAlmSecEn='true' and ../crcPerAlmLspEn='false')";
            default "false";
            description
              "Configure PER(packet error ratio) of crc-error trigger LSP.";
            ext:allowDelete "true";
          }
          leaf crcPerAlmSecEn {
            when "not(../../portHardType='AtmPort') or ../crcPerAlmEn='true'";
            type boolean;
            must "not(../crcPerAlmLspEn='true') or (../crcPerAlmLspEn='true' and ../crcPerAlmSecEn='false')";
            default "false";
            description
              "Configure PER(packet error ratio) of crc-error trigger section.";
            ext:allowDelete "true";
          }
          leaf crcPerCur {
            when "not(../../portHardType='AtmPort')";
            type string {
              length "0..8";
            }
            config false;
            description
              "Current Value of packet error ratio.";
            ext:allowDelete "true";
          }
          leaf phyUpDownEn {
            when "not(../../portHardType='AtmPort')";
            type boolean;
            default "true";
            description
              "phyUpDownEn.";
            ext:allowDelete "true";
          }
          leaf crcMfeAlmEn {
            when "not(../../portHardType='AtmPort' or ../linkQAlmEn='true')";
            type boolean;
            default "false";
            description
              "Enalbe or disable the crc MFE alarm.";
            ext:allowDelete "true";
          }
          leaf crcMfeAlmThrCoefficient {
            when "not(../../portHardType='AtmPort') or ../crcMfeAlmEn='true'";
            type uint32 {
              range "1..9";
            }
            mandatory true;
            description
              "mac fcs exc coefficient (x of xE-y). The range is 1 to 9. ";
            ext:allowDelete "true";
          }
          leaf crcMfeAlmThrPower {
            when "not(../../portHardType='AtmPort') or ../crcMfeAlmEn='true'";
            type uint32 {
              range "2..5";
            }
            mandatory true;
            description
              "mac fcs exc exponent (y of xE-y). The range is 2 to 5.";
            ext:allowDelete "true";
          }
          leaf crcMfeRsumThrCoefficient {
            when "not(../../portHardType='AtmPort') or ../crcMfeAlmEn='true' or ../crcMfeAlmThrCoefficient and ../crcMfeAlmThrCoefficient!=0 and ../crcMfeAlmThrPower and ../crcMfeAlmThrPower!=0";
            type uint32 {
              range "1..9";
            }
            mandatory true;
            description
              "mac fcs exc coefficient (x of xE-y). The range is 1 to 9. ";
            ext:allowDelete "true";
          }
          leaf crcMfeRsumThrPower {
            when "not(../../portHardType='AtmPort') or ../crcMfeAlmEn='true' or ../crcMfeAlmThrCoefficient and ../crcMfeAlmThrCoefficient!=0 and ../crcMfeAlmThrPower and ../crcMfeAlmThrPower!=0";
            type uint32 {
              range "2..6";
            }
            mandatory true;
            description
              "For resume-threshold: mac fcs exc exponent (y of xE-y). The range is 2 to 6.";
            ext:allowDelete "true";
          }
          leaf crcMfeAlmLspEn {
            when "not(../../portHardType='AtmPort') or ../crcMfeAlmEn='true'";
            type boolean;
            default "false";
            description
              "Configure MFE(mac fcs exc) of crc-error trigger LSP.";
            ext:allowDelete "true";
          }
          leaf crcMfsAlmEn {
            when "not(../../portHardType='AtmPort' or ../linkQAlmEn='true')";
            type boolean;
            default "false";
            description
              "Enalbe or disable the crc MFS alarm.";
            ext:allowDelete "true";
          }
          leaf crcMfsAlmThrCoefficient {
            when "not(../../portHardType='AtmPort') or ../crcMfsAlmEn='true'";
            type uint32 {
              range "1..9";
            }
            mandatory true;
            description
              "mac fcs sd coefficient (x of xE-y). The range is 1 to 9. ";
            ext:allowDelete "true";
          }
          leaf crcMfsAlmThrPower {
            when "not(../../portHardType='AtmPort') or ../crcMfsAlmEn='true'";
            type uint32 {
              range "5..9";
            }
            mandatory true;
            description
              "mac fcs sd exponent (y of xE-y). The range is 5 to 9.";
            ext:allowDelete "true";
          }
          leaf crcMfsRsumThrCoefficient {
            when "not(../../portHardType='AtmPort') or ../crcMfsAlmEn='true' or ../crcMfsAlmThrCoefficient and ../crcMfsAlmThrCoefficient!=0 and ../crcMfsAlmThrPower and ../crcMfsAlmThrPower!=0";
            type uint32 {
              range "1..9";
            }
            mandatory true;
            description
              "mac fcs sd coefficient (x of xE-y). The range is 1 to 9. ";
            ext:allowDelete "true";
          }
          leaf crcMfsRsumThrPower {
            when "not(../../portHardType='AtmPort') or ../crcMfsAlmEn='true' or ../crcMfsAlmThrCoefficient and ../crcMfsAlmThrCoefficient!=0 and ../crcMfsAlmThrPower and ../crcMfsAlmThrPower!=0";
            type uint32 {
              range "5..10";
            }
            mandatory true;
            description
              "For resume-threshold: mac fcs sd exponent (y of xE-y). The range is 5 to 10.";
            ext:allowDelete "true";
          }
          leaf crcMfsAlmLspEn {
            when "not(../../portHardType='AtmPort') or ../crcMfsAlmEn='true'";
            type boolean;
            default "false";
            description
              "Configure MFS(mac fcs sd) of crc-error trigger LSP.";
            ext:allowDelete "true";
          }
          leaf linkQAlmEn {
            when "not(../../portHardType='AtmPort')";
            type boolean;
            default "false";
            description
              "Enalbe or disable the link-quality alarm.";
            ext:allowDelete "true";
          }
          leaf linkQAlmThrCoefficient {
            when "not(../../portHardType='AtmPort') or ../linkQAlmEn='true'";
            type uint32 {
              range "1..9";
            }
            mandatory true;
            description
              "INTEGER<1-9>  Trigger coefficient. ";
            ext:allowDelete "true";
          }
          leaf linkQAlmThrPower {
            when "not(../../portHardType='AtmPort') or ../linkQAlmEn='true'";
            type uint32 {
              range "1..7";
            }
            mandatory true;
            description
              "INTEGER<1-7>  Trigger power.";
            ext:allowDelete "true";
          }
          leaf linkQRsumThrCoefficient {
            when "not(../../portHardType='AtmPort') or ../linkQAlmEn='true'";
            type uint32 {
              range "1..9";
            }
            mandatory true;
            description
              "INTEGER<1-9>  Recovery coefficient. ";
            ext:allowDelete "true";
          }
          leaf linkQRsumThrPower {
            when "not(../../portHardType='AtmPort') or ../linkQAlmEn='true'";
            type uint32 {
              range "1..7";
            }
            mandatory true;
            description
              "INTEGER<1-7>  Recovery power.";
            ext:allowDelete "true";
          }
          container ethPortAlarmInfo {
            when "not(../../portHardType='PosPort') or ../../portType='GE'";
            description
              "Ethernet port alarm information.";
            leaf symbolEnabledDown {
              type boolean;
              default "false";
              description
                "Symbol error enable eown.";
              ext:allowDelete "true";
            }
            leaf symbolErrorHighThreshold {
              type uint32 {
                range "1..4294967295";
              }
              units "number of invalid packets";
              default "1000";
              description
                "Symbol error high threshold.";
              ext:allowDelete "true";
            }
            leaf symbolErrorLowThreshold {
              type uint32 {
                range "1..4294967295";
              }
              units "number of invalid packets";
              default "100";
              description
                "Symbol error low threshold.";
              ext:allowDelete "true";
            }
            leaf symbolErrorInterval {
              type uint32 {
                range "1..65535";
              }
              units s;
              default "10";
              description
                "Symbol error interval.";
              ext:allowDelete "true";
            }
            leaf bip8SdEnabledDown {
              type boolean;
              default "false";
              description
                "BIP8-SD error enable eown.";
              ext:allowDelete "true";
            }
            leaf bip8SdErrorHighThreshold {
              type uint32 {
                range "6..9";
              }
              units "power of 10";
              default "6";
              description
                "BIP8-SD error high threshold.";
              ext:allowDelete "true";
            }
            leaf badBytesThreshold {
              type uint32 {
                range "1..65535";
              }
              units "number of invalid bytes";
              default "1000";
              description
                "badBytesThreshold.";
              ext:allowDelete "true";
            }
            leaf badBytesInterval {
              type uint32 {
                range "1..65535";
              }
              units s;
              default "10";
              description
                "badBytesInterval.";
              ext:allowDelete "true";
            }
            leaf txPauseErrorHighThreshold {
              type uint32 {
                range "1..4294967295";
              }
              units "number of invalid packets";
              default "500";
              description
                "Tx-pause error high threshold.";
              ext:allowDelete "true";
            }
            leaf txPauseErrorLowThreshold {
              type uint32 {
                range "1..4294967295";
              }
              units "number of invalid packets";
              default "100";
              description
                "Tx-pause error Low Threshold.";
              ext:allowDelete "true";
            }
            leaf txPauseErrorInterval {
              type uint32 {
                range "1..65535";
              }
              units s;
              default "10";
              description
                "Tx-pause error Interval.";
              ext:allowDelete "true";
            }
          }
          container sdhPortAlarmInfo {
            when "not(../../portHardType!='PosPort' and ../../portHardType!='EthWANPort' and ../../ethernetPort/transMode!='wanMode' and ../../portHardType!='AtmPort')";
            description
              "SDH port alarm information.";
            leaf sdhEnabledDown {
              type boolean;
              default "false";
              description
                "SDH error enable eown.";
              ext:allowDelete "true";
            }
            leaf sdhErrorHighThreshold {
              type uint32 {
                range "1..4294967295";
              }
              units "number of invalid packets";
              default "1000";
              description
                "SDH error high threshold.";
              ext:allowDelete "true";
            }
            leaf sdhErrorLowThreshold {
              type uint32 {
                range "1..4294967295";
              }
              units "number of invalid packets";
              default "100";
              description
                "SDH error low threshold.";
              ext:allowDelete "true";
            }
            leaf sdhErrorInterval {
              type uint32 {
                range "1..65535";
              }
              units s;
              default "10";
              description
                "SDH error interval.";
              ext:allowDelete "true";
            }
            leaf sdhB1ErrThreshold {
              type uint32 {
                range "1..65535";
              }
              units s;
              default "1000";
              description
                "B1 Error Threshold.";
              ext:allowDelete "true";
            }
            leaf sdhB2ErrThreshold {
              type uint32 {
                range "1..65535";
              }
              units s;
              default "1000";
              description
                "B2 Error Threshold.";
              ext:allowDelete "true";
            }
            leaf sdhB1ErrInterval {
              type uint32 {
                range "1..65535";
              }
              units s;
              default "10";
              description
                "B1 error interval.";
              ext:allowDelete "true";
            }
            leaf sdhB2ErrInterval {
              type uint32 {
                range "1..65535";
              }
              units s;
              default "10";
              description
                "B2 error interval.";
              ext:allowDelete "true";
            }
          }
        }
        container transAlarmInfo {
          when "not(../portHardType!='EthWANPort' and ../portHardType!='PosPort' and ../portHardType!='OtnPort' and ../ethernetPort/transMode!='wanMode' and ../portHardType!='CposPort' and ../portHardType!='E1Port' and ../portHardType!='E3Port' and ../portHardType!='AtmPort' or ../portHardType='ADMCHANNEL' or ../portHardType='ADMLINEPORT' or ../portHardType='EthMGEPort')";
          description
            "TAD Alarm Information.";
          leaf dampSuppress {
            type uint32 {
              range "2..19999";
            }
            default "2000";
            description
              "TAD Alarm Damp Suppress Value.";
            ext:allowDelete "true";
          }
          leaf dampReuse {
            type uint32 {
              range "1..19998";
            }
            default "750";
            description
              "TAD Alarm Reuse Value.";
            ext:allowDelete "true";
          }
          leaf dampCeiling {
            type uint32 {
              range "1001..20000";
            }
            default "6000";
            description
              "TAD Alarm Ceiling Value.";
            ext:allowDelete "true";
          }
          leaf dampDecayOk {
            type uint32 {
              range "500..10000";
            }
            units ms;
            default "1000";
            description
              "TAD Alarm OK Half Decay Value.";
            ext:allowDelete "true";
          }
          leaf dampDecayNg {
            type uint32 {
              range "500..10000";
            }
            units ms;
            default "1000";
            description
              "TAD Alarm NG Half Decay Value.";
            ext:allowDelete "true";
          }
          leaf holdoffTimer {
            type uint32 {
              range "20..10000";
            }
            units ms;
            default "50";
            description
              "TAD Hold Down Time.";
            ext:allowDelete "true";
          }
          leaf holdupTimer {
            type uint32 {
              range "200..3600000";
            }
            units ms;
            default "300";
            description
              "TAD Hold Up Time.";
            ext:allowDelete "true";
          }
          leaf thresholdB3tca {
            when "not(../../e1t1Port/workMode or ../../portHardType='E1Port' or ../../portHardType='E3Port')";
            type uint32 {
              range "3..9";
            }
            units 10e-n;
            default "6";
            description
              "TAD Alarm B3tca Threshold.";
            ext:allowDelete "true";
          }
          leaf thresholdB1tca {
            when "not(../../e1t1Port/workMode or ../../portHardType='E1Port' or ../../portHardType='E3Port')";
            type uint32 {
              range "3..9";
            }
            units 10e-n;
            default "6";
            description
              "TAD Alarm B1tca Threshold.";
            ext:allowDelete "true";
          }
          leaf thresholdB2tca {
            when "not(../../e1t1Port/workMode or ../../portHardType='E1Port' or ../../portHardType='E3Port')";
            type uint32 {
              range "3..9";
            }
            units 10e-n;
            default "6";
            description
              "TAD Alarm B2tca Threshold.";
            ext:allowDelete "true";
          }
          leaf thresholdSdbere {
            when "not(../../e1t1Port/workMode or ../../portHardType='E1Port' or ../../portHardType='E3Port')";
            type uint32 {
              range "3..9";
            }
            units 10e-n;
            default "6";
            description
              "TAD Alarm Sdbere Threshold.";
            ext:allowDelete "true";
          }
          leaf thresholdSfbere {
            when "not(../../e1t1Port/workMode or ../../portHardType='E1Port' or ../../portHardType='E3Port')";
            type uint32 {
              range "3..9";
            }
            units 10e-n;
            default "3";
            description
              "TAD Alarm Sfbere Threshold.";
            ext:allowDelete "true";
          }
          leaf almLastresettime {
            type yang:date-and-time;
            config false;
            description
              "TAD Last Reset Time.";
          }
          leaf filterFunction {
            type boolean;
            default "false";
            config false;
            description
              "TAD Alarm Filter Function.";
          }
          leaf dampingFunction {
            type boolean;
            default "false";
            config false;
            description
              "TAD Alarm Damping Function.";
          }
          container transAlarmIfDowns {
            description
              "TAD Alarm Status Information.";
            list transAlarmIfDown {
              key "alarmType";
              description
                "TAD Alarm Status Information.";
              leaf alarmType {
                type devm_transAlarmType_type;
                description
                  "TAD Alarm Type.";
              }
              leaf ifDown {
                type boolean;
                default "false";
                description
                  "TAD Alarm If down.";
                ext:allowDelete "true";
              }
              leaf alarmStatus {
                type boolean;
                default "false";
                config false;
                description
                  "TAD Alarm True Or False.";
              }
              leaf IsInFiltering {
                type boolean;
                default "false";
                config false;
                description
                  "TAD Alarm Is In Filtering.";
              }
              leaf IsInSuppressing {
                type boolean;
                default "false";
                config false;
                description
                  "TAD Alarm Is In Suppressing.";
              }
              leaf IsInAging {
                type boolean;
                default "false";
                config false;
                description
                  "TAD Alarm Is In Aging.";
              }
              leaf flappingCount {
                type uint32 {
                  range "0..4294967295";
                }
                config false;
                description
                  "TAD Alarm Flapping Count.";
              }
              leaf suppressingCount {
                type uint32 {
                  range "0..4294967295";
                }
                config false;
                description
                  "TAD Alarm Suppressing Count.";
              }
              leaf figureOfMerit {
                type string {
                  length "0..16";
                }
                config false;
                description
                  "TAD Alarm Figure Of Merit.";
              }
            }
          }
        }
        container admPort {
          when "not(../portHardType!='ADMCHANNEL' and ../portHardType!='ADMLINEPORT')";
          description
            "ADM Port.";
          leaf rxPower {
            type string {
              length "0..64";
            }
            config false;
            description
              "Receive power.";
          }
          leaf txPower {
            type string {
              length "0..64";
            }
            config false;
            description
              "Transmit power.";
          }
          leaf descriton {
            type string {
              length "1..242";
            }
            default "NA";
            description
              "Adm port description.";
            ext:allowDelete "true";
          }
          leaf waveLength {
            type string {
              length "0..8";
            }
            config false;
            description
              "length of wave";
          }
          leaf conectRelation {
            when "not(../../portHardType='ADMLINEPORT')";
            type leafref {
              path "/ifm:ifm/ifm:interfaces/ifm:interface/ifm:ifName";
            }
            description
              "Connection Relation.";
            ext:allowDelete "true";
          }
          leaf direction {
            type string {
              length "0..8";
            }
            config false;
            description
              "direction.";
          }
          leaf waveBand {
            type string {
              length "0..8";
            }
            config false;
            description
              "waveBand.";
          }
          leaf waveLengthNo {
            type string {
              length "0..8";
            }
            config false;
            description
              "waveLengthNo.";
          }
        }
        container laser {
          when "not(../portHardType='ADMCHANNEL' or ../portHardType='ADMLINEPORT') or ../mediumType='fiber'";
          description
            "Laser.";
          leaf laserAutoShut {
            type devmlaserautoshutType;
            default "disable";
            description
              "Laser auto shut.";
            ext:allowDelete "true";
          }
          leaf laserOpenTime {
            type uint32 {
              range "100..300";
            }
            default "200";
            description
              "LaserOpenTime(10ms).";
            ext:allowDelete "true";
          }
          leaf laserCloseTime {
            type uint32 {
              range "200..30000";
            }
            default "6000";
            description
              "LaserCloseTime(10ms).";
            ext:allowDelete "true";
          }
          leaf laserStatus {
            type devmlaserstatusType;
            default "on";
            config false;
            description
              "LaserStatus.";
          }
        }
        container atmPort {
          when "not(../portHardType!='AtmPort') or ../portHardType='AtmPort'";
          description
            "ATM Port.";
          leaf clock {
            type devmSdhClockType;
            default "master";
            description
              "Clock Mode.";
            ext:allowDelete "true";
          }
          leaf scramble {
            type devmScrambleType;
            default "enabled";
            description
              "Scramble.";
            ext:allowDelete "true";
          }
          leaf j0Mode {
            type devmAtmFlagModeType;
            must "((../j0Mode='16byte' or ../j0Mode='peer') )";
            default "16byte";
            description
              "j0Mode (ATM).";
            ext:allowDelete "true";
          }
          leaf j0Value {
            when "not(../j0Mode='16byte' or ../j0Mode='64byte' or ../j0Mode='peer') or ../j0Mode='1byte'";
            type uint32 {
              range "0..127";
            }
            description
              "j0Value (ATM).";
            ext:allowDelete "true";
          }
          leaf j0Trace {
            when "not(../j0Mode='1byte' or ../j0Mode='peer') or ../j0Mode='16byte' or ../j0Mode='64byte'";
            type string {
              length "1..62";
            }
            default "NetEngine";
            description
              "j0Trace (ATM).";
          }
          leaf j1Mode {
            type devmAtmFlagModeType;
            must "((../j1Mode='16byte' or ../j1Mode='64byte' or ../j1Mode='peer') )";
            default "16byte";
            description
              "j1Mode (ATM).";
            ext:allowDelete "true";
          }
          leaf j1Value {
            when "not(../j1Mode='16byte' or ../j1Mode='64byte' or ../j1Mode='peer') or ../j1Mode='1byte'";
            type uint32 {
              range "0..127";
            }
            description
              "j1Value (ATM).";
            ext:allowDelete "true";
          }
          leaf j1Trace {
            when "not(../j1Mode='1byte' or ../j1Mode='peer') or ../j1Mode='16byte' or ../j1Mode='64byte'";
            type string {
              length "1..62";
            }
            default "NetEngine";
            description
              "j1Trace (ATM).";
          }
          leaf c2Value {
            type uint32 {
              range "0..255";
            }
            default "19";
            description
              "c2Value (ATM).";
            ext:allowDelete "true";
          }
          leaf rxj0Mode {
            type devmAtmFlagModeType;
            config false;
            description
              "rxj0Mode of a ATM port.";
          }
          leaf rxj0Value {
            type uint32 {
              range "0..127";
            }
            config false;
            description
              "rxj0Value (ATM).";
          }
          leaf rxj0Trace {
            type string {
              length "0..64";
            }
            config false;
            description
              "rxj0Trace (ATM).";
          }
          leaf rxj1Mode {
            type devmAtmFlagModeType;
            config false;
            description
              "rxj1Mode of a ATM port.";
          }
          leaf rxj1Value {
            type uint32 {
              range "0..127";
            }
            config false;
            description
              "rxj1Value (ATM).";
          }
          leaf rxj1Trace {
            type string {
              length "0..64";
            }
            config false;
            description
              "rxj1Trace (ATM).";
          }
          leaf rxc2Value {
            type uint32 {
              range "0..255";
            }
            config false;
            description
              "rxc2Value (ATM).";
          }
          leaf holdUp {
            type devmHoldupType;
            default "disabled";
            description
              "holdUp(ATM).";
            ext:allowDelete "true";
          }
          leaf lbHoldTime {
            when "../../loopbackMode!='noLoopback' and ../../portHardType='AtmPort'";
            type uint32 {
              range "0..43200";
            }
            default "0";
            description
              "Loopback AutoClear Period.";
            ext:allowDelete "true";
          }
        }
      }
    }
    container remotePorts {
      description
        "remotePorts.";
      list remotePort {
        key "ifIndex";
        description
          "remotePort.";
        leaf ifIndex {
          type uint32 {
            range "1..4294967295";
          }
          description
            "Remote Port Index.";
        }
        leaf ifName {
          type string {
            length "0..64";
          }
          config false;
          description
            "Remote Port Name.";
        }
        leaf portTxEnDelay {
          type uint32 {
            range "0..86400000";
          }
          default "0";
          description
            "Port Tx Enable Delay.";
          ext:allowDelete "false";
        }
        container opticalInfo {
          description
            "Information about optical transceivers.";
          leaf optRxHighWarnEn {
            type boolean;
            default "true";
            description
              "Receive optical power high warning.";
            ext:allowDelete "true";
          }
          leaf optRxLowWarnEn {
            type boolean;
            default "true";
            description
              "Receive optical power low warning.";
            ext:allowDelete "true";
          }
          leaf optTxHighWarnEn {
            type boolean;
            default "true";
            description
              "Transmit optical power high warning.";
            ext:allowDelete "true";
          }
          leaf optTxLowWarnEn {
            type boolean;
            default "true";
            description
              "Transmit optical power low warning.";
            ext:allowDelete "true";
          }
          leaf waveLengthChannelNum {
            type devmTunableWaveLengthType;
            default "No-configurable";
            description
              "Tunable optical module wave length.";
          }
          leaf optVoltHWarnEn {
            type boolean;
            default "true";
            description
              "Optical module voltage high warning.";
            ext:allowDelete "true";
          }
          leaf optVoltLWarnEn {
            type boolean;
            default "true";
            description
              "Optical module voltage low warning.";
            ext:allowDelete "true";
          }
        }
        container ethernetPort {
          description
            "Ethernet port.";
          leaf flowctl {
            type devmFlowCtlType;
            default "defaultConfig";
            description
              "Flow control method of an Ethernet port.";
            ext:allowDelete "true";
          }
          leaf downHoldTime {
            when "not(../transMode='wanMode') or ../transMode='lanMode'";
            type uint32 {
              range "0..86400000";
            }
            default "0";
            description
              "down hold time.";
            ext:allowDelete "true";
          }
          leaf upHoldTime {
            when "not(../transMode='wanMode') or ../transMode='lanMode'";
            type uint32 {
              range "0..86400000";
            }
            default "200";
            description
              "up hold time.";
            ext:allowDelete "true";
          }
          leaf transMode {
            type devmRemoteportLanWanModeType;
            default "lanMode";
            description
              "transmit mode of an Ethernet port.";
            ext:allowDelete "true";
          }
          leaf gfMediaType {
            when "not(../transMode='wanMode') or ../transMode='lanMode'";
            type devmGfMediaType;
            default "auto";
            description
              "Medium type on an Ethernet GF port.";
            ext:allowDelete "true";
          }
          leaf holdUp {
            type devmHoldupType;
            default "disabled";
            description
              "Whether the hold-up function is configured on a Ethernet port. ";
            ext:allowDelete "true";
          }
          leaf negoMode {
            when "not(../transMode='wanMode') or ../transMode='lanMode'";
            type devmnegoModeType;
            default "NA";
            description
              "Auto Negotiation Mode.";
            ext:allowDelete "true";
          }
          leaf negotiation {
            type devmNegoPatchType;
            default "default";
            description
              "Auto negotiation on an Ethernet port.";
            ext:allowDelete "true";
          }
          container ethWANAttr {
            when "not(../transMode='lanMode')";
            description
              "Ethernet port attributes.";
            leaf frameFormat {
              when "../../transMode='wanMode'";
              type devmFrameFormatType;
              default "SDH";
              description
                "Frame format of a WAN port.";
              ext:allowDelete "true";
            }
            leaf j0Mode {
              when "../../transMode='wanMode'";
              type devmWANSdhFlagModeType;
              default "16byte";
              description
                "j0 mode on an Ethernet WAN port.";
              ext:allowDelete "true";
            }
            leaf j0Value {
              when "not(../j0Mode='16byte' or ../j0Mode='64byte-or-null-mode') or ../j0Mode='1byte'";
              type uint32 {
                range "0..255";
              }
              description
                "Vaule of j0Mode on an Ethernet WAN port.";
              ext:allowDelete "true";
            }
            leaf j0Trace {
              when "not(../j0Mode='1byte') or ../j0Mode='16byte' or ../j0Mode='64byte-or-null-mode'";
              type string {
                length "0..62";
              }
              default "NA";
              description
                "Description of the j0 mode on an Ethernet WAN port.";
            }
            leaf j1Mode {
              when "../../transMode='wanMode'";
              type devmWANSdhFlagModeType;
              default "16byte";
              description
                "j1 mode on an Ethernet WAN port on an Ethernet WAN port.";
              ext:allowDelete "true";
            }
            leaf j1Value {
              when "not(../j1Mode='16byte' or ../j1Mode='64byte-or-null-mode') or ../j1Mode='1byte'";
              type uint32 {
                range "0..255";
              }
              description
                "Value of j1Mode on an Ethernet WAN port.";
              ext:allowDelete "true";
            }
            leaf j1Trace {
              when "not(../j1Mode='1byte') or ../j1Mode='16byte' or ../j1Mode='64byte-or-null-mode'";
              type string {
                length "0..62";
              }
              default "NA";
              description
                "Description of the j1 mode on an Ethernet WAN port.";
            }
            leaf c2 {
              when "../../transMode='wanMode'";
              type uint32 {
                range "0..255";
              }
              default "26";
              description
                "C2 mode on an Ethernet WAN port.";
              ext:allowDelete "true";
            }
            leaf clock {
              when "../../transMode='wanMode'";
              type devmSdhClockType;
              default "master";
              description
                "Active/standby clock on an Ethernet WAN port. ";
              ext:allowDelete "true";
            }
            leaf scramble {
              when "../../transMode='wanMode'";
              type devmScrambleType;
              default "enabled";
              description
                "Whether the scrambling function is configured on an Ethernet WAN port. ";
              ext:allowDelete "true";
            }
          }
        }
        container portAlarmInfo {
          description
            "Port alarm information.";
          leaf crcEnabledDown {
            when "not(../crcPerAlmEn='true' or ../linkQAlmEn='true')";
            type boolean;
            default "false";
            description
              "CRC error enable eown.";
            ext:allowDelete "true";
          }
          leaf crcErrorHighThreshold {
            when "not(../crcPerAlmEn='true' or ../linkQAlmEn='true')";
            type uint32 {
              range "1..4294967295";
            }
            units "number of invalid packets";
            default "1000";
            description
              "CRC error high threshold.";
            ext:allowDelete "true";
          }
          leaf crcErrorLowThreshold {
            when "not(../crcPerAlmEn='true' or ../linkQAlmEn='true')";
            type uint32 {
              range "1..4294967295";
            }
            units "number of invalid packets";
            default "100";
            description
              "CRC error low threshold.";
            ext:allowDelete "true";
          }
          leaf crcErrorInterval {
            when "not(../crcPerAlmEn='true' or ../linkQAlmEn='true')";
            type uint32 {
              range "1..65535";
            }
            units s;
            default "10";
            description
              "CRC error interval.";
            ext:allowDelete "true";
          }
          leaf crcShutDownEn {
            when "not(../crcPerAlmEn='true' or ../linkQAlmEn='true')";
            type boolean;
            default "false";
            description
              "crc ShutDown.";
            ext:allowDelete "true";
          }
          leaf crcErrorPercentAlmThr {
            when "not(../crcPerAlmEn='true' or ../linkQAlmEn='true')";
            type uint32 {
              range "0..100";
            }
            units percentage;
            default "0";
            description
              "crcErrorPercentAlmThr.";
            ext:allowDelete "true";
          }
          leaf inputEnabledDown {
            type boolean;
            default "false";
            description
              "Input error enable eown.";
            ext:allowDelete "true";
          }
          leaf inputErrorHighThreshold {
            type uint32 {
              range "1..4294967295";
            }
            units "number of invalid packets";
            default "1000";
            description
              "Input error high threshold.";
            ext:allowDelete "true";
          }
          leaf inputErrorLowThreshold {
            type uint32 {
              range "1..4294967295";
            }
            units "number of invalid packets";
            default "100";
            description
              "Input error low threshold.";
            ext:allowDelete "true";
          }
          leaf inputErrorInterval {
            type uint32 {
              range "1..65535";
            }
            units s;
            default "10";
            description
              "Input error interval.";
            ext:allowDelete "true";
          }
          leaf outputEnabledDown {
            type boolean;
            default "false";
            description
              "Output error enable eown.";
            ext:allowDelete "true";
          }
          leaf outputErrorHighThreshold {
            type uint32 {
              range "1..4294967295";
            }
            units "number of invalid packets";
            default "1000";
            description
              "Output error high threshold.";
            ext:allowDelete "true";
          }
          leaf outputErrorLowThreshold {
            type uint32 {
              range "1..4294967295";
            }
            units "number of invalid packets";
            default "100";
            description
              "Output error low threshold.";
            ext:allowDelete "true";
          }
          leaf outputErrorInterval {
            type uint32 {
              range "1..65535";
            }
            units s;
            default "10";
            description
              "Output error interval.";
            ext:allowDelete "true";
          }
          leaf crcPerAlmEn {
            type boolean;
            default "false";
            description
              "Enalbe or disable the crc PER alarm.";
            ext:allowDelete "true";
          }
          leaf crcPerAlmThrCoefficient {
            when "../crcPerAlmEn='true'";
            type uint32 {
              range "1..9";
            }
            mandatory true;
            description
              "Packet error ratio coefficient (x of xE-y). The range is 1 to 9. ";
            ext:allowDelete "true";
          }
          leaf crcPerAlmThrPower {
            when "../crcPerAlmEn='true'";
            type uint32 {
              range "1..5";
            }
            mandatory true;
            description
              "Packet error ratio exponent (y of xE-y). The range is 1 to 5.";
            ext:allowDelete "true";
          }
          leaf crcPerRsumThrCoefficient {
            when "../crcPerAlmEn='true'";
            type uint32 {
              range "1..9";
            }
            mandatory true;
            description
              "Packet error ratio coefficient (x of xE-y). The range is 1 to 9. ";
            ext:allowDelete "true";
          }
          leaf crcPerRsumThrPower {
            when "../crcPerAlmEn='true'";
            type uint32 {
              range "1..6";
            }
            mandatory true;
            description
              "For resume-threshold: Packet error ratio exponent (y of xE-y). The range is 1 to 6.";
            ext:allowDelete "true";
          }
          leaf crcPerSampWinFactor {
            when "../crcPerAlmEn='true'";
            type uint32 {
              range "10..100";
            }
            mandatory true;
            description
              "Sample window factor, default is 50.";
            ext:allowDelete "true";
          }
          leaf crcPerChildWinMaxNum {
            when "../crcPerAlmEn='true'";
            type uint32 {
              range "10..100";
            }
            mandatory true;
            description
              "Maximum number of child windows, default is 50.";
            ext:allowDelete "true";
          }
          leaf crcPerChildWinAlarmNum {
            when "../crcPerAlmEn='true'";
            type uint32 {
              range "1..100";
            }
            mandatory true;
            description
              "Minimal number of child windows for alarm generating, default is 5.";
            ext:allowDelete "true";
          }
          leaf crcPerChildWinResumeNum {
            when "../crcPerAlmEn='true'";
            type uint32 {
              range "1..100";
            }
            mandatory true;
            description
              "Minimal number of child windows for alarm resuming, default is 30.";
            ext:allowDelete "true";
          }
          leaf crcAlgRealtimeFactor {
            when "../crcPerAlmEn='true'";
            type uint32 {
              range "0..10";
            }
            mandatory true;
            description
              "crcAlgRealtimeFactor.";
            ext:allowDelete "true";
          }
          leaf crcPerAlmLspEn {
            when "../crcPerAlmEn='true'";
            type boolean;
            must "not(../crcPerAlmSecEn='true') or (../crcPerAlmSecEn='true' and ../crcPerAlmLspEn='false')";
            default "false";
            description
              "Configure PER(packet error ratio) of crc-error trigger LSP.";
            ext:allowDelete "true";
          }
          leaf crcPerAlmSecEn {
            when "../crcPerAlmEn='true'";
            type boolean;
            must "not(../crcPerAlmLspEn='true') or (../crcPerAlmLspEn='true' and ../crcPerAlmSecEn='false')";
            default "false";
            description
              "Configure PER(packet error ratio) of crc-error trigger section.";
            ext:allowDelete "true";
          }
          leaf phyUpDownEn {
            type boolean;
            default "true";
            description
              "phyUpDownEn.";
            ext:allowDelete "true";
          }
          leaf linkQAlmEn {
            type boolean;
            default "false";
            description
              "Enalbe or disable the link-quality alarm.";
            ext:allowDelete "true";
          }
          leaf linkQAlmThrCoefficient {
            when "../linkQAlmEn='true'";
            type uint32 {
              range "1..9";
            }
            mandatory true;
            description
              "INTEGER<1-9>  Trigger coefficient. ";
            ext:allowDelete "true";
          }
          leaf linkQAlmThrPower {
            when "../linkQAlmEn='true'";
            type uint32 {
              range "1..7";
            }
            mandatory true;
            description
              "INTEGER<1-7>  Trigger power.";
            ext:allowDelete "true";
          }
          leaf linkQRsumThrCoefficient {
            when "../linkQAlmEn='true'";
            type uint32 {
              range "1..9";
            }
            mandatory true;
            description
              "INTEGER<1-9>  Recovery coefficient. ";
            ext:allowDelete "true";
          }
          leaf linkQRsumThrPower {
            when "../linkQAlmEn='true'";
            type uint32 {
              range "1..7";
            }
            mandatory true;
            description
              "INTEGER<1-7>  Recovery power.";
            ext:allowDelete "true";
          }
          container ethPortAlarmInfo {
            description
              "Ethernet port alarm information.";
            leaf symbolEnabledDown {
              type boolean;
              default "false";
              description
                "Symbol error enable eown.";
              ext:allowDelete "true";
            }
            leaf symbolErrorHighThreshold {
              type uint32 {
                range "1..4294967295";
              }
              units "number of invalid packets";
              default "1000";
              description
                "Symbol error high threshold.";
              ext:allowDelete "true";
            }
            leaf symbolErrorLowThreshold {
              type uint32 {
                range "1..4294967295";
              }
              units "number of invalid packets";
              default "100";
              description
                "Symbol error low threshold.";
              ext:allowDelete "true";
            }
            leaf symbolErrorInterval {
              type uint32 {
                range "1..65535";
              }
              units s;
              default "10";
              description
                "Symbol error interval.";
              ext:allowDelete "true";
            }
            leaf bip8SdEnabledDown {
              type boolean;
              default "false";
              description
                "BIP8-SD error enable eown.";
              ext:allowDelete "true";
            }
            leaf bip8SdErrorHighThreshold {
              type uint32 {
                range "6..9";
              }
              units "power of 10";
              default "6";
              description
                "BIP8-SD error high threshold.";
              ext:allowDelete "true";
            }
            leaf badBytesThreshold {
              type uint32 {
                range "1..65535";
              }
              units "number of invalid bytes";
              default "1000";
              description
                "badBytesThreshold.";
              ext:allowDelete "true";
            }
            leaf badBytesInterval {
              type uint32 {
                range "1..65535";
              }
              units s;
              default "10";
              description
                "badBytesInterval.";
              ext:allowDelete "true";
            }
            leaf txPauseErrorHighThreshold {
              type uint32 {
                range "1..4294967295";
              }
              units "number of invalid packets";
              default "500";
              description
                "Tx-pause error high threshold.";
              ext:allowDelete "true";
            }
            leaf txPauseErrorLowThreshold {
              type uint32 {
                range "1..4294967295";
              }
              units "number of invalid packets";
              default "100";
              description
                "Tx-pause error Low Threshold.";
              ext:allowDelete "true";
            }
            leaf txPauseErrorInterval {
              type uint32 {
                range "1..65535";
              }
              units s;
              default "10";
              description
                "Tx-pause error Interval.";
              ext:allowDelete "true";
            }
          }
          container sdhPortAlarmInfo {
            when "not(../../ethernetPort/transMode='lanMode') or ../../ethernetPort/transMode='wanMode'";
            description
              "SDH port alarm information.";
            leaf sdhEnabledDown {
              type boolean;
              default "false";
              description
                "SDH error enable eown.";
              ext:allowDelete "true";
            }
            leaf sdhErrorHighThreshold {
              type uint32 {
                range "1..4294967295";
              }
              units "number of invalid packets";
              default "1000";
              description
                "SDH error high threshold.";
              ext:allowDelete "true";
            }
            leaf sdhErrorLowThreshold {
              type uint32 {
                range "1..4294967295";
              }
              units "number of invalid packets";
              default "100";
              description
                "SDH error low threshold.";
              ext:allowDelete "true";
            }
            leaf sdhErrorInterval {
              type uint32 {
                range "1..65535";
              }
              units s;
              default "10";
              description
                "SDH error interval.";
              ext:allowDelete "true";
            }
            leaf sdhB1ErrThreshold {
              type uint32 {
                range "1..65535";
              }
              units s;
              default "1000";
              description
                "B1 Error Threshold.";
              ext:allowDelete "true";
            }
            leaf sdhB2ErrThreshold {
              type uint32 {
                range "1..65535";
              }
              units s;
              default "1000";
              description
                "B2 Error Threshold.";
              ext:allowDelete "true";
            }
            leaf sdhB1ErrInterval {
              type uint32 {
                range "1..65535";
              }
              units s;
              default "10";
              description
                "B1 error interval.";
              ext:allowDelete "true";
            }
            leaf sdhB2ErrInterval {
              type uint32 {
                range "1..65535";
              }
              units s;
              default "10";
              description
                "B2 error interval.";
              ext:allowDelete "true";
            }
          }
        }
        container transAlarmInfo {
          when "not(../ethernetPort/transMode='lanMode') or ../ethernetPort/transMode='wanMode'";
          description
            "TAD Alarm Information.";
          leaf dampSuppress {
            type uint32 {
              range "2..19999";
            }
            default "2000";
            description
              "TAD Alarm Damp Suppress Value.";
            ext:allowDelete "true";
          }
          leaf dampReuse {
            type uint32 {
              range "1..19998";
            }
            default "750";
            description
              "TAD Alarm Reuse Value.";
            ext:allowDelete "true";
          }
          leaf dampCeiling {
            type uint32 {
              range "1001..20000";
            }
            default "6000";
            description
              "TAD Alarm Ceiling Value.";
            ext:allowDelete "true";
          }
          leaf dampDecayOk {
            type uint32 {
              range "500..10000";
            }
            units ms;
            default "1000";
            description
              "TAD Alarm OK Half Decay Value.";
            ext:allowDelete "true";
          }
          leaf dampDecayNg {
            type uint32 {
              range "500..10000";
            }
            units ms;
            default "1000";
            description
              "TAD Alarm NG Half Decay Value.";
            ext:allowDelete "true";
          }
          leaf holdoffTimer {
            type uint32 {
              range "20..10000";
            }
            units ms;
            default "50";
            description
              "TAD Hold Down Time.";
            ext:allowDelete "true";
          }
          leaf holdupTimer {
            type uint32 {
              range "200..3600000";
            }
            units ms;
            default "300";
            description
              "TAD Hold Up Time.";
            ext:allowDelete "true";
          }
          leaf thresholdB3tca {
            type uint32 {
              range "3..9";
            }
            units 10e-n;
            default "6";
            description
              "TAD Alarm B3tca Threshold.";
            ext:allowDelete "true";
          }
          leaf thresholdB1tca {
            type uint32 {
              range "3..9";
            }
            units 10e-n;
            default "6";
            description
              "TAD Alarm B1tca Threshold.";
            ext:allowDelete "true";
          }
          leaf thresholdB2tca {
            type uint32 {
              range "3..9";
            }
            units 10e-n;
            default "6";
            description
              "TAD Alarm B2tca Threshold.";
            ext:allowDelete "true";
          }
          leaf thresholdSdbere {
            type uint32 {
              range "3..9";
            }
            units 10e-n;
            default "6";
            description
              "TAD Alarm Sdbere Threshold.";
            ext:allowDelete "true";
          }
          leaf thresholdSfbere {
            type uint32 {
              range "3..9";
            }
            units 10e-n;
            default "3";
            description
              "TAD Alarm Sfbere Threshold.";
            ext:allowDelete "true";
          }
          container transAlarmIfDowns {
            description
              "TAD Alarm Status Information.";
            list transAlarmIfDown {
              key "alarmType";
              description
                "TAD Alarm Status Information.";
              leaf alarmType {
                type devm_transAlarmType_type;
                description
                  "TAD Alarm Type.";
              }
              leaf ifDown {
                type boolean;
                default "false";
                description
                  "TAD Alarm If down.";
                ext:allowDelete "true";
              }
            }
          }
        }
        container laser {
          description
            "Laser.";
          leaf laserAutoShut {
            type devmlaserautoshutType;
            default "disable";
            description
              "Laser auto shut.";
            ext:allowDelete "true";
          }
          leaf laserOpenTime {
            type uint32 {
              range "100..300";
            }
            default "200";
            description
              "LaserOpenTime(10ms).";
            ext:allowDelete "true";
          }
          leaf laserCloseTime {
            type uint32 {
              range "200..30000";
            }
            default "6000";
            description
              "LaserCloseTime(10ms).";
            ext:allowDelete "true";
          }
        }
      }
    }
    container boardResStates {
      config false;
      description
        "Board monitoring information.";
      list boardResState {
        key "boardPosition";
        config false;
        description
          "Board monitoring information.";
        leaf boardPosition {
          type string {
            length "0..32";
          }
          config false;
          description
            "Board position.";
        }
        leaf entIndex {
          type uint32;
          config false;
          description
            "Board index.";
        }
        leaf boardName {
          type string {
            length "0..128";
          }
          config false;
          description
            "Board name.";
        }
        leaf cpuUsage {
          type uint32;
          units %;
          config false;
          description
            "CPU usage.";
        }
        leaf memTotalSize {
          type uint32;
          units "M Bytes";
          config false;
          description
            "Total memory size.";
        }
        leaf memUsedSize {
          type uint32;
          units "M Bytes";
          config false;
          description
            "Used memory size.";
        }
        leaf memoryUsage {
          type uint32;
          units %;
          config false;
          description
            "Memory usage.";
        }
      }
    }
    container cpuInfos {
      description
        "State information about a board CPU.";
      list cpuInfo {
        key "position";
        description
          "State information about a board CPU.";
        leaf position {
          type string {
            length "0..32";
          }
          description
            "Board position.";
        }
        leaf entIndex {
          type uint32;
          config false;
          description
            "Board index.";
        }
        leaf systemCpuUsage {
          type uint32 {
            range "0..100";
          }
          default "0";
          config false;
          description
            "CPU usage.";
          ext:support-filter "false";
        }
        leaf ovloadThreshold {
          type uint32 {
            range "4..100";
          }
          default "4";
          description
            "Overload threshold.";
          ext:support-filter "false";
        }
        leaf unovloadThreshold {
          type uint32 {
            range "1..97";
          }
          default "1";
          description
            "Unoverload threshold should be 3 less than Overload threshold.";
          ext:support-filter "false";
        }
      }
    }
    container memoryInfos {
      description
        "Memory information about a board.";
      list memoryInfo {
        key "position";
        description
          "Memory information about a board.";
        leaf position {
          type string {
            length "0..32";
          }
          description
            "Board position.";
        }
        leaf entIndex {
          type uint32;
          config false;
          description
            "Board index.";
        }
        leaf osMemoryTotal {
          type uint32;
          config false;
          description
            "Total OS memory.";
          ext:support-filter "false";
        }
        leaf osMemoryUse {
          type uint32;
          config false;
          description
            "Used OS memory.";
          ext:support-filter "false";
        }
        leaf osMemoryFree {
          type uint32;
          config false;
          description
            "Free OS memory.";
          ext:support-filter "false";
        }
        leaf osMemoryUsage {
          type uint32 {
            range "0..100";
          }
          default "0";
          config false;
          description
            "OS memory usage.";
          ext:support-filter "false";
        }
        leaf doMemoryTotal {
          type uint32;
          config false;
          description
            "Total VRP memory.";
          ext:support-filter "false";
        }
        leaf doMemoryUse {
          type uint32;
          config false;
          description
            "Used VRP memory.";
          ext:support-filter "false";
        }
        leaf doMemoryFree {
          type uint32;
          config false;
          description
            "Free VRP memory. ";
          ext:support-filter "false";
        }
        leaf doMemoryUsage {
          type uint32 {
            range "0..100";
          }
          default "0";
          config false;
          description
            "VRP memory usage.";
          ext:support-filter "false";
        }
        leaf simpleMemoryTotal {
          type uint32;
          config false;
          description
            "Total simple memory. ";
          ext:support-filter "false";
        }
        leaf simpleMemoryUse {
          type uint32;
          config false;
          description
            "Used simple memory. ";
          ext:support-filter "false";
        }
        leaf simpleMemoryFree {
          type uint32;
          config false;
          description
            "Free simple memory. ";
          ext:support-filter "false";
        }
        leaf simpleMemoryUsage {
          type uint32 {
            range "0..100";
          }
          default "0";
          config false;
          description
            "Simple memory usage.";
          ext:support-filter "false";
        }
        leaf ovloadThreshold {
          type uint32 {
            range "75..100";
          }
          default "75";
          description
            "Overload threshold.";
          ext:support-filter "false";
        }
        leaf unovloadThreshold {
          type uint32 {
            range "1..97";
          }
          default "1";
          description
            "Unoverload threshold.";
          ext:support-filter "false";
        }
      }
    }
    container cmuSwitchAlms {
      description
        "CMUs.";
      list cmuSwitchAlm {
        key "position cmuSwitchId";
        description
          "CMU.";
        leaf position {
          type string {
            length "0..32";
          }
          description
            "CMU Position.";
        }
        leaf cmuAlmEn {
          type boolean;
          config false;
          mandatory true;
          description
            "CMU AlarmEn.";
        }
        leaf cmuSwitchId {
          type uint32 {
            range "0..3";
          }
          description
            "CMU SwitchId.";
        }
        leaf cmuAlarmMode {
          type uint32 {
            range "0..1";
          }
          must "not(../cmuAlmEn='false')";
          mandatory true;
          description
            "CMU AlarmMode.";
        }
        leaf cmuSwitchName {
          type devmCmuSwitchName;
          must "not(../cmuAlmEn='false')";
          mandatory true;
          description
            "CMU SwitchName.";
        }
        leaf userDefinedName {
          type string {
            length "0..64";
          }
          must "../cmuSwitchName='unknown' or not(../cmuAlmEn='false')";
          mandatory true;
          description
            "UserDefinedName.";
        }
      }
    }
    container temperatureInfos {
      description
        "Temperature information about a board.";
      list temperatureInfo {
        key "position i2c address channel";
        description
          "Temperature information about a board.";
        leaf position {
          type string {
            length "0..32";
          }
          description
            "Board position.";
        }
        leaf pcbName {
          type string {
            length "0..32";
          }
          config false;
          description
            "Board type.";
        }
        leaf i2c {
          type uint32;
          description
            "I2C bus number.";
        }
        leaf address {
          type string {
            length "0..255";
          }
          description
            "Sensor address.";
        }
        leaf channel {
          type uint32;
          description
            "Number of a sensor channel.";
        }
        leaf entIndex {
          type uint32;
          config false;
          description
            "Board index.";
        }
        leaf state {
          type devmTempVoltStateType;
          config false;
          description
            "Sensor state information.";
        }
        leaf currentTemperature {
          type int32;
          config false;
          description
            "Current temperature.";
        }
        leaf minorAlmThreshold {
          type uint32;
          config false;
          description
            "Minor temperature alarm threshold.";
        }
        leaf majorAlmThreshold {
          type uint32;
          config false;
          description
            "Major temperature alarm threshold.";
        }
        leaf fatalAlmThreshold {
          type uint32;
          config false;
          description
            "Fatal temperature alarm threshold.";
        }
        leaf minor {
          type uint32 {
            range "0..120";
          }
          default "80";
          description
            "Minor Threshold.";
        }
        leaf major {
          type uint32 {
            range "0..120";
          }
          default "90";
          description
            "Major Threshold.";
        }
        leaf fatal {
          type uint32 {
            range "0..120";
          }
          default "100";
          description
            "Fatal Threshold.";
        }
        leaf fanTmax {
          type int32 {
            range "-50..127";
          }
          default "95";
          description
            "Fan Speed Adjust High Threshold.[-50,127]for get operation,[1,100]for edit operation.";
        }
        leaf fanTmin {
          type int32 {
            range "-50..127";
          }
          default "80";
          description
            "Fan Speed Adjust Low Threshold.[-50,127]for get operation,[1,100]for edit operation.";
        }
      }
    }
    container voltageInfos {
      description
        "Voltage information about a board.";
      list voltageInfo {
        key "position i2c address channel";
        description
          "Voltage information about a board.";
        leaf position {
          type string {
            length "0..32";
          }
          description
            "Board position.";
        }
        leaf pcbName {
          type string {
            length "0..32";
          }
          config false;
          description
            "Board type.";
        }
        leaf i2c {
          type uint32;
          description
            "I2C bus number.";
        }
        leaf address {
          type string {
            length "0..255";
          }
          description
            "Sensor address.";
        }
        leaf channel {
          type uint32;
          description
            "Sensor channel.";
        }
        leaf entIndex {
          type uint32;
          config false;
          description
            "Board index.";
        }
        leaf state {
          type devmTempVoltStateType;
          config false;
          description
            "Voltage sensor state.";
        }
        leaf currentVoltage {
          type string {
            length "0..255";
          }
          config false;
          description
            "Current voltage value.";
        }
        leaf requiredVoltage {
          type string {
            length "0..255";
          }
          config false;
          description
            "Required voltage value.";
        }
        leaf majorlowThreshold {
          type string {
            length "0..255";
          }
          config false;
          description
            "Major Lower voltage threshold.";
        }
        leaf lowThreshold {
          type string {
            length "0..255";
          }
          config false;
          description
            "Fatal Lower voltage threshold.";
        }
        leaf majorhighThreshold {
          type string {
            length "0..255";
          }
          config false;
          description
            "Major Upper voltage threshold.";
        }
        leaf highThreshold {
          type string {
            length "0..255";
          }
          config false;
          description
            "Fatal Upper voltage threshold.";
        }
        leaf voltageRatio {
          type string {
            length "0..255";
          }
          config false;
          description
            "Voltage Ratio.";
        }
        leaf vltMajorL {
          type uint32 {
            range "0..120";
          }
          default "80";
          description
            "The percentage of the major voltage threshold below the default voltage.";
        }
        leaf vltMajorH {
          type uint32 {
            range "0..120";
          }
          default "80";
          description
            "The percentage of the major voltage threshold above the default voltage.";
        }
        leaf vltFatalL {
          type uint32 {
            range "0..120";
          }
          default "80";
          description
            "The percentage of the fatal voltage threshold below the default voltage.";
        }
        leaf vltFatalH {
          type uint32 {
            range "0..120";
          }
          default "80";
          description
            "The percentage of the fatal voltage threshold above the default voltage.";
        }
      }
    }
    container areaEnergyInfos {
      config false;
      description
        "Area Energy.";
      list areaEnergyInfo {
        key "chassisPos areaID";
        config false;
        description
          "Area Energy.";
        leaf chassisPos {
          type string {
            length "0..32";
          }
          config false;
          description
            "Chassis Position.";
        }
        leaf areaID {
          type uint32;
          config false;
          description
            "Area ID.";
        }
        leaf areaRatedPower {
          type string {
            length "0..255";
          }
          config false;
          description
            "Area Rated Power.";
        }
        leaf areaUsedPower {
          type string {
            length "0..255";
          }
          config false;
          description
            "Area Used Power";
        }
        leaf areaLeftPower {
          type string {
            length "0..255";
          }
          config false;
          description
            "Area Left Power";
        }
        container brdEnergyInfos {
          config false;
          description
            "Energy information about a board.";
          list brdEnergyInfo {
            key "position";
            config false;
            description
              "Energy information about a board.";
            leaf position {
              type string {
                length "0..32";
              }
              config false;
              description
                "Board position.";
            }
            leaf entIndex {
              type uint32;
              config false;
              description
                "Board index.";
            }
            leaf pcbName {
              type string {
                length "0..32";
              }
              config false;
              description
                "Board type.";
            }
            leaf voltageValue {
              type string {
                length "0..255";
              }
              config false;
              description
                "Current voltage value.";
            }
            leaf electricalValue {
              type string {
                length "0..255";
              }
              config false;
              description
                "Current electrical value.";
            }
            leaf currentPower {
              type string {
                length "0..255";
              }
              config false;
              description
                "Current power value.";
            }
            leaf ratedPower {
              type string {
                length "0..255";
              }
              config false;
              description
                "Rated power value.";
            }
            leaf powerThreshold {
              type string {
                length "0..255";
              }
              config false;
              description
                "Power threshold value.";
            }
            leaf efficiency {
              type string {
                length "0..255";
              }
              config false;
              description
                "Efficiency value.";
            }
          }
        }
      }
    }
    container entityClasss {
      config false;
      description
        "Entity capabilities.";
      list entityClass {
        key "className";
        config false;
        description
          "Entity capability.";
        leaf className {
          type devmEntityClassType;
          config false;
          description
            "Entity type.";
        }
        leaf isResetable {
          type boolean;
          config false;
          description
            "Whether the entity can be reset.";
        }
        leaf isSwitchoverable {
          type boolean;
          config false;
          description
            "Whether a switchover can be performed on the entity.";
        }
      }
    }
    container innerLinks {
      config false;
      description
        "Inner links.";
      list innerLink {
        key "linkType leftChassisPosition rightChassisPosition";
        config false;
        description
          "Inner link.";
        leaf linkIndex {
          type string {
            length "0..64";
          }
          config false;
          description
            "Inner link index.";
        }
        leaf linkName {
          type string {
            length "0..64";
          }
          config false;
          description
            "Inner link name.";
        }
        leaf linkType {
          type devmInnerlinkType;
          config false;
          description
            "Link type.";
        }
        leaf leftChassisPosition {
          type string {
            length "0..32";
          }
          config false;
          description
            "Position of the left chassis. ";
        }
        leaf leftChassisType {
          type devmChassisSvcType;
          config false;
          description
            "Type of the left chassis.";
        }
        leaf rightChassisPosition {
          type string {
            length "0..32";
          }
          config false;
          description
            "Position of the right chassis.";
        }
        leaf rightChassisType {
          type devmChassisSvcType;
          config false;
          description
            "Type of the right chassis. ";
        }
        leaf operState {
          type devmInnerLinkOperStateType;
          config false;
          description
            "Operation state.";
        }
        leaf alarmState {
          type devmInnerLinkAlarmType;
          config false;
          description
            "Alarm states whose values inherit HUAWEI-INNER-LINK-MIB.";
        }
        leaf ccchalfChassisPos {
          type devmHalfChassisPos;
          config false;
          description
            "Position of ccc half chassis ";
        }
        leaf phyCXPSN {
          type string {
            length "0..15";
          }
          config false;
          description
            "CXP sequence number";
        }
        leaf phyCXPLength {
          type uint32;
          config false;
          description
            "CXP fiber Physical length";
        }
        leaf fiberCFGLength {
          type uint32;
          config false;
          description
            "CXP fiber configurable length";
        }
        leaf leftCXPstatus {
          type devmEntityOperState;
          config false;
          description
            "CXP left status";
        }
        leaf rightCXPstatus {
          type devmEntityOperState;
          config false;
          description
            "CXP right status";
        }
        container phyInnerLinks {
          config false;
          description
            "Physical inner links.";
          list phyInnerLink {
            config false;
            description
              "Physical inner link.";
            leaf phyInnerLinkName {
              type string {
                length "0..128";
              }
              config false;
              description
                "Physical link name.";
            }
            leaf leftPortName {
              type string {
                length "0..128";
              }
              config false;
              description
                "Left port name.";
              ext:support-filter "true";
            }
            leaf rightPortName {
              type string {
                length "0..128";
              }
              config false;
              description
                "Right port name.";
              ext:support-filter "true";
            }
            leaf phyOperStatus {
              type devmEntityOperState;
              config false;
              description
                "Operation status.";
            }
            leaf repairId {
              type uint32;
              config false;
              description
                "Repair ID.";
            }
            leaf repairDescr {
              type string {
                length "0..255";
              }
              config false;
              description
                "Repair description.";
            }
            container checkPoints {
              config false;
              description
                "Check points.";
              list checkPoint {
                key "index";
                config false;
                description
                  "Check point.";
                leaf index {
                  type string {
                    length "0..255";
                  }
                  config false;
                  description
                    "Check point index.";
                }
                leaf entityName {
                  type string {
                    length "0..255";
                  }
                  config false;
                  description
                    "Check point name.";
                }
                leaf entityClass {
                  type devmEntityClassType;
                  config false;
                  description
                    "Check point type.";
                }
                leaf status {
                  type devmEntityOperState;
                  config false;
                  description
                    "Check point status.";
                }
                leaf reasonId {
                  type uint32;
                  config false;
                  description
                    "Reason ID.";
                }
                leaf reasonDescr {
                  type string {
                    length "0..255";
                  }
                  config false;
                  description
                    "Reason description.";
                }
                leaf repairId {
                  type uint32;
                  config false;
                  description
                    "Repair ID.";
                }
                leaf repairDescr {
                  type string {
                    length "0..255";
                  }
                  config false;
                  description
                    "Repair description.";
                }
              }
            }
          }
        }
      }
    }
    container dntmStats {
      config false;
      description
        "TM statitics info.";
      list dntmStat {
        key "position chipid";
        config false;
        description
          "TM statitics info.";
        leaf position {
          type string {
            length "0..50";
          }
          config false;
          description
            "position.";
        }
        leaf chipid {
          type string {
            length "0..50";
          }
          config false;
          description
            "chipid.";
        }
        leaf np2FabInPkts {
          type string {
            length "0..255";
          }
          config false;
          description
            "Np2FbricInPkts.";
        }
        leaf np2FabDropPkts {
          type string {
            length "0..255";
          }
          config false;
          description
            "Np2FbricDropPkts.";
        }
        leaf np2FabOutCells {
          type string {
            length "0..255";
          }
          config false;
          description
            "Np2FbricOutCells.";
        }
        leaf fab2NpInCells {
          type string {
            length "0..255";
          }
          config false;
          description
            "Fbric2NpInCells.";
        }
        leaf fab2NpInPkts {
          type string {
            length "0..255";
          }
          config false;
          description
            "Fbric2NpInPkts.";
        }
        leaf fab2NpDropPkts {
          type string {
            length "0..255";
          }
          config false;
          description
            "Fbric2NpDropPkts.";
        }
        leaf fab2NpOutPkts {
          type string {
            length "0..255";
          }
          config false;
          description
            "Fbric2NpOutPkts.";
        }
      }
    }
    container dnfabStats {
      config false;
      description
        "Fabric statitics info.";
      list dnfabStat {
        key "position chipid";
        config false;
        description
          "Fabfic statitic info.";
        leaf position {
          type string {
            length "0..50";
          }
          config false;
          description
            "SFU position.";
        }
        leaf chipid {
          type string {
            length "0..50";
          }
          config false;
          description
            "chipid.";
        }
        leaf inCells {
          type string {
            length "0..255";
          }
          config false;
          description
            "In Cells.";
        }
        leaf dropCells {
          type string {
            length "0..255";
          }
          config false;
          description
            "Drop Cells.";
        }
        leaf outCells {
          type string {
            length "0..255";
          }
          config false;
          description
            "Out Cells.";
        }
      }
    }
    container rUModuleInfos {
      config false;
      description
        "Electronic labels.";
      list rUModuleInfo {
        key "entClass position entSerialNo";
        config false;
        description
          "Electronic label.";
        leaf entClass {
          type devmEntityClassType;
          config false;
          description
            "Class.";
        }
        leaf position {
          type string {
            length "0..32";
          }
          config false;
          description
            "Position.";
        }
        leaf entSerialNo {
          type string {
            length "0..32";
          }
          config false;
          description
            "Physical number.";
        }
        leaf entIndex {
          type uint32;
          config false;
          description
            "Index.";
        }
        leaf entBomId {
          type string {
            length "0..128";
          }
          config false;
          description
            "BOM ID.";
        }
        leaf entSerialNum {
          type string {
            length "0..128";
          }
          config false;
          description
            "Serial number.";
        }
        leaf entBomEnDesc {
          type string {
            length "0..256";
          }
          config false;
          description
            "English description of a BOM. ";
        }
        leaf entBomLocalDesc {
          type string {
            length "0..256";
          }
          config false;
          description
            "Local description of a BOM.";
        }
        leaf entMfgName {
          type string {
            length "0..128";
          }
          config false;
          description
            "Manufacturer name.";
        }
        leaf entManufacturedDate {
          type string {
            length "0..128";
          }
          config false;
          description
            "Manufacture date.";
        }
        leaf entManufactureCode {
          type string {
            length "0..128";
          }
          config false;
          description
            "Manufacture code.";
        }
        leaf entBoardType {
          type string {
            length "0..128";
          }
          config false;
          description
            "Board type.";
        }
        leaf entAssetID {
          type string {
            length "0..128";
          }
          config false;
          description
            "Asset ID.";
        }
        leaf entCLEICode {
          type string {
            length "0..128";
          }
          config false;
          description
            "CLEI code.";
        }
        leaf entUpdateLog {
          type string {
            length "0..128";
          }
          config false;
          description
            "Update log.";
        }
        leaf entArchivesInfoVersion {
          type string {
            length "0..128";
          }
          config false;
          description
            "Archives information version.";
        }
        leaf entOpenBomId {
          type string {
            length "0..128";
          }
          config false;
          description
            "The BomId for distribution.";
        }
        leaf entIssueNum {
          type string {
            length "0..128";
          }
          config false;
          description
            "Issue number.";
        }
      }
    }
    container hardwareInfos {
      config false;
      description
        "Hardware compatibility information.";
      list hardwareInfo {
        key "hardwareName";
        config false;
        description
          "Hardware compatibility information.";
        leaf hardwareName {
          type devmHardType;
          config false;
          description
            "Hardware name.";
        }
        leaf hardwareType {
          type devmEntityClassType;
          config false;
          description
            "Hardware type.";
        }
      }
    }
    container ccus {
      config false;
      description
        "CCU info.";
      list ccu {
        config false;
        description
          "CCU info.";
        leaf softwareVersion {
          type string {
            length "0..32";
          }
          config false;
          description
            "CCU version.";
        }
      }
    }
    container isAlmInsertAisRdiFlags {
      description
        "Alarm Insert Ais Configuration.";
      list isAlmInsertAisRdiFlag {
        key "almName";
        description
          "Alarm Insert Ais Configuration.";
        leaf almName {
          type devmInsertAisAlmType;
          description
            "Alarm Name.";
        }
        leaf insertAisFlag {
          when "not(../almName='hptimatm' or ../almName='hpuneqatm')";
          type boolean;
          default "false";
          description
            "Alarm Insert Ais Enable.";
        }
        leaf almRdiFlag {
          when "not(../almName='rstim')";
          type boolean;
          default "false";
          description
            "Peer Alarm Report RDI Enable.";
        }
      }
    }
    container offlineCfgs {
      config false;
      description
        "Offline configurations.";
      list offlineCfg {
        key "entClass position";
        config false;
        description
          "Offline configuration.";
        leaf entClass {
          type devmOfflineType;
          config false;
          description
            "Class.";
        }
        leaf position {
          type string {
            length "0..32";
          }
          config false;
          description
            "Position.";
        }
      }
    }
    container vsuSerInfos {
      description
        "VSUF Service Types.";
      list vsuSerInfo {
        key "slotId";
        description
          "VSUF Service Type.";
        leaf slotId {
          type string {
            length "0..32";
          }
          description
            "Slot.";
        }
        leaf curVsuSerType {
          type devmVsuSerType;
          config false;
          description
            "VSUF CurServ Type.";
        }
        leaf nextVsuSerType {
          type devmVsuSerType;
          default "hts";
          description
            "VSUF NextServ Type.";
        }
      }
    }
    container panelSplitPorts {
      description
        "Panel Ports.";
      list panelSplitPort {
        key "position";
        description
          "Panel Port.";
        leaf position {
          type string {
            length "0..32";
          }
          description
            "Panel Port Position.";
        }
        leaf splitType {
          type devmSplitTypeEnum;
          must "not(../position) or (../position and (../splitType='4*10GE' or ../splitType='1*100GE' or ../splitType='10*10GE' or ../splitType='1*40GE') )";
          default "none";
          description
            "Panel Port Splittype.";
        }
        container splitPortInfos {
          config false;
          description
            "Split Ports.";
          list splitPortInfo {
            key "splitPosition";
            config false;
            description
              "Split Port.";
            leaf splitPosition {
              type string {
                length "0..32";
              }
              config false;
              description
                "Split Port Position.";
            }
            leaf portName {
              type pub-type:ifName;
              config false;
              description
                "Split Port Name.";
            }
          }
        }
      }
    }
    container clkSyncNodes {
      config false;
      description
        "ClkSyncNode.";
      list clkSyncNode {
        key "slotId";
        config false;
        description
          "ClkSyncNode.";
        leaf brdDevtype {
          type devmboardDevType;
          config false;
          description
            "BrdDevtype.";
        }
        leaf slotId {
          type string {
            length "0..32";
          }
          config false;
          description
            "SlotId.";
        }
        leaf clkType {
          type devmclockType;
          config false;
          description
            "ClkType.";
        }
        leaf clkSlotId {
          type string {
            length "0..32";
          }
          config false;
          description
            "ClkSlotId.";
        }
        leaf switchMode {
          type devmswitchModeType;
          config false;
          description
            "SwitchMode.";
        }
        leaf lockStat {
          type devmlockStatType;
          config false;
          description
            "LockStat.";
        }
      }
    }
    container clkLineNodes {
      config false;
      description
        "ClkLineNode.";
      list clkLineNode {
        key "slotId";
        config false;
        description
          "ClkLineNode.";
        leaf brdDevtype {
          type devmboardDevType;
          config false;
          description
            "ClkSlotId.";
        }
        leaf slotId {
          type string {
            length "0..32";
          }
          config false;
          description
            "ClkType.";
        }
        leaf clkType {
          type devmclockType;
          config false;
          description
            "SlotId.";
        }
        leaf clkSlotId {
          type string {
            length "0..32";
          }
          config false;
          description
            "BrdDevtype.";
        }
        leaf switchMode {
          type devmswitchModeType;
          config false;
          description
            "SwitchMode.";
        }
      }
    }
    container upgradeStatNodes {
      config false;
      description
        "UpgradeStatus.";
      list upgradeStatNode {
        key "slotId";
        config false;
        description
          "UpgradeStatus.";
        leaf slotId {
          type string {
            length "0..32";
          }
          config false;
          description
            "SlotId.";
        }
        leaf brdDevtype {
          type string {
            length "0..32";
          }
          config false;
          description
            "BrdDevtype.";
        }
        leaf loading {
          type string {
            length "0..32";
          }
          config false;
          description
            "Loading.";
        }
        leaf waiting {
          type string {
            length "0..32";
          }
          config false;
          description
            "Waiting.";
        }
        leaf startTime {
          type string {
            length "0..32";
          }
          config false;
          description
            "StartTime.";
        }
        leaf process {
          type string {
            length "0..32";
          }
          config false;
          description
            "Progress.";
        }
      }
    }
    container intfMatchCheckNodes {
      description
        "IntfMatchCheckNodes.";
      list intfMatchCheckNode {
        key "slotID cardID";
        description
          "IntfMatchCheckNode.";
        leaf object {
          type devmintfMatchCheckNodeObject;
          default "chassis";
          description
            "Object.";
        }
        leaf slotID {
          type string {
            length "1..30";
          }
          description
            "SlotID.";
        }
        leaf cardID {
          type string {
            length "1..30";
          }
          description
            "CardID.";
        }
        leaf undoFlag {
          type devmintfMatchCheckNodeFlag;
          must "(../object='chassis' and (../undoFlag='enable' or ../undoFlag='disable') ) or ((not(../object='chassis') and (../undoFlag='enable') ))";
          default "enable";
          description
            "UndoFlag.";
        }
      }
    }
    container boardExTestActNodes {
      config false;
      description
        "Mbus Node Information.";
      list boardExTestActNode {
        key "slotID";
        config false;
        description
          "Mbus Node Information.";
        leaf slotID {
          type string {
            length "1..30";
          }
          config false;
          description
            "Position.";
        }
        leaf registerStr {
          type string {
            length "1..63";
          }
          config false;
          description
            "Register State.";
        }
        leaf boardtype {
          type string {
            length "1..63";
          }
          config false;
          description
            "Board Type.";
        }
        leaf eepromNo {
          type uint32 {
            range "0..24";
          }
          config false;
          description
            "Eeprom Number.";
        }
        leaf tempMonNo {
          type uint32 {
            range "0..128";
          }
          config false;
          description
            "Temperature Monitor Number.";
        }
        leaf voltMonNo {
          type uint32 {
            range "0..128";
          }
          config false;
          description
            "Voltage Monitor Number.";
        }
      }
    }
    container chsIdInfoNodes {
      description
        "Chassis Info.";
      list chsIdInfoNode {
        key "chassisid";
        description
          "Chassis Info.";
        leaf chassistype {
          type devmMultiChassisType;
          config false;
          description
            "Chassistype.";
        }
        leaf chassisid {
          type uint32 {
            range "1..2";
          }
          description
            "Current chassisid.";
        }
        leaf nextchassisid {
          type uint32 {
            range "1..2";
          }
          default "1";
          description
            "Next chassisid.";
        }
      }
    }
    container chsRunModeNodes {
      description
        "Chassis run mode.";
      list chsRunModeNode {
        key "chassisid";
        description
          "Chassis run mode.";
        leaf chassisid {
          type string {
            length "1..31";
          }
          description
            "Chassisid.";
        }
        leaf curmode {
          type devmRunModeType;
          config false;
          description
            "Current run mode.";
        }
        leaf nextmode {
          type devmRunModeType;
          default "single";
          config false;
          description
            "Next run mode.";
        }
        leaf setnextmode {
          type devmSetType;
          default "YES";
          description
            "Set virtual-cluster.";
        }
        leaf curcluster {
          type string {
            length "1..4";
          }
          config false;
          description
            "Current clusterid.";
        }
        leaf nextcluster {
          type string {
            length "1..4";
          }
          default "NA";
          description
            "Next clusterid.";
        }
      }
    }
    container currentInfos {
      config false;
      description
        "Current information about a board.";
      list currentInfo {
        key "position i2c address channel";
        config false;
        description
          "Current information about a board.";
        leaf position {
          type string {
            length "0..50";
          }
          config false;
          description
            "Board position.";
        }
        leaf pcbName {
          type string {
            length "0..50";
          }
          config false;
          description
            "Board type.";
        }
        leaf i2c {
          type uint32;
          config false;
          description
            "I2C bus number.";
        }
        leaf address {
          type string {
            length "0..50";
          }
          config false;
          description
            "Sensor address.";
        }
        leaf channel {
          type uint32;
          config false;
          description
            "Sensor channel.";
        }
        leaf state {
          type devmTempVoltStateType;
          config false;
          description
            "Voltage sensor state.";
        }
        leaf current {
          type string {
            length "0..50";
          }
          config false;
          description
            "Current value.";
        }
        leaf requiredCurrent {
          type string {
            length "0..50";
          }
          config false;
          description
            "Required current value.";
        }
        leaf fatalLThreshold {
          type string {
            length "0..50";
          }
          config false;
          description
            "Fatal Lower Current threshold.";
        }
        leaf fatalHThreshold {
          type string {
            length "0..50";
          }
          config false;
          description
            "Fatal Upper Current Threshold.";
        }
        leaf majorLThreshold {
          type string {
            length "0..50";
          }
          config false;
          description
            "Major Lower Current Threshold.";
        }
        leaf majorHThreshold {
          type string {
            length "0..50";
          }
          config false;
          description
            "Major Upper Current Threshold.";
        }
      }
    }
    container slaveDefaults {
      description
        "Slave Default.";
      list slaveDefault {
        key "chassisid slotID";
        description
          "Slave Default.";
        leaf chassisid {
          type string {
            length "0..32";
          }
          description
            "Chassis ID.";
        }
        leaf slotID {
          type string {
            length "0..32";
          }
          description
            "Slot ID.";
        }
        leaf slaveDefault {
          type string {
            length "0..64";
          }
          default "NA";
          description
            "Slave Default,Input the SlotID:The MPU SlotID; or NA:clear the Slave Default.";
        }
      }
    }
  }
}
