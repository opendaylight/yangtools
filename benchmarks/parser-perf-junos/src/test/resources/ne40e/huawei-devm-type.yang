/*
Copyright (C) 2013-2017 Huawei Technologies Co., Ltd. All rights reserved.
*/
submodule huawei-devm-type {
  belongs-to huawei-devm {
    prefix devm;
  }
  
  organization
    "Huawei Technologies Co.,Ltd.";
  contact
    "Huawei Industrial Base Bantian, Longgang Shenzhen 518129                    
        People's Republic of China                    
        Website: http://www.huawei.com Email: support@huawei.com";
  description
    "devm_type";
  revision 2017-03-23 {
    description
      "Functions supported by the schema are added to the YANG file.";
    reference
      "Huawei private.";
  }
  revision 2013-01-01 {
    description
      "Init revision";
    reference
      "Huawei private.";
  }
  typedef devmEntityClassType {
    type enumeration {
      enum "other" {
        description
          "Other.";
      }
      enum "unknown" {
        description
          "Unknown.";
      }
      enum "chassis" {
        description
          "Chassis.";
      }
      enum "backplane" {
        description
          "Backplane.";
      }
      enum "container" {
        description
          "Slot.";
      }
      enum "mpuModule" {
        description
          "MPU.";
      }
      enum "lpuModule" {
        description
          "LPU.";
      }
      enum "sfuModule" {
        description
          "SFU.";
      }
      enum "ecuModule" {
        description
          "ECU.";
      }
      enum "icuModule" {
        description
          "ICU.";
      }
      enum "cmuModule" {
        description
          "CMU.";
      }
      enum "clockModule" {
        description
          "CLK.";
      }
      enum "fan" {
        description
          "Fan.";
      }
      enum "powerSupply" {
        description
          "Power supply.";
      }
      enum "PMU" {
        description
          "PMU.";
      }
      enum "PM" {
        description
          "PM.";
      }
      enum "lcd" {
        description
          "LCD.";
      }
      enum "cfModule" {
        description
          "CF card.";
      }
      enum "flexibleCardModule" {
        description
          "Flexible card.";
      }
      enum "port" {
        description
          "Port.";
      }
      enum "sensor" {
        description
          "Sensor.";
      }
    }
    description
      "Physical entity class";
  }
  typedef devmOfflineType {
    type enumeration {
      enum "chassis" {
        description
          "Chassis.";
      }
      enum "board" {
        description
          "Board.";
      }
      enum "card" {
        description
          "Card position.";
      }
    }
    description
      "";
  }
  typedef devmContainerType {
    type enumeration {
      enum "unknown" {
        description
          "Unknown.";
      }
      enum "boardSlot" {
        description
          "Board slot.";
      }
      enum "mpuSlot" {
        description
          "MPU slot.";
      }
      enum "lpuSlot" {
        description
          "LPU slot.";
      }
      enum "sfuSlot" {
        description
          "SFU slot.";
      }
      enum "icuSlot" {
        description
          "ICU slot.";
      }
      enum "ecuSlot" {
        description
          "ECU slot.";
      }
      enum "clkSlot" {
        description
          "CLK slot.";
      }
      enum "cmuSlot" {
        description
          "CMU slot.";
      }
      enum "fanSlot" {
        description
          "Fan slot.";
      }
      enum "powerSlot" {
        description
          "Power slot.";
      }
      enum "PmuSlot" {
        description
          "PMU slot.";
      }
      enum "pmuSlot" {
        description
          "PMU slot.";
      }
      enum "lcdSlot" {
        description
          "LCD slot.";
      }
      enum "picSlot" {
        description
          "Pic slot.";
      }
      enum "ofcSlot" {
        description
          "Ofc slot.";
      }
      enum "cfcardSlot" {
        description
          "CFCARD slot.";
      }
      enum "virtualSlot" {
        description
          "Virtual slot.";
      }
      enum "virtualSubSlot" {
        description
          "Virtual sub slot.";
      }
    }
    description
      "";
  }
  typedef devmChassisType {
    type enumeration {
      enum "unknown" {
        description
          "Unknown.";
      }
      enum "fname8090Unknown" {
        description
          "Unknown.";
      }
      enum "fname8090Whole" {
        description
          "NE5000E chassis.";
      }
      enum "fname8090NE5000EX" {
        description
          "NE5000EX chassis.";
      }
      enum "fname8090ClusterCentral" {
        description
          "NE5000E cluster central chassis.";
      }
      enum "fname8090NE5000EX-VB" {
        description
          "NE5000EX-VB chassis.";
      }
      enum "fname8090NE5000EX-A" {
        description
          "NE5000EX16A Chassis.";
      }
      enum "fname8090NE5000ENGCCC" {
        description
          "NE5000ENGCCC Chassis.";
      }
      enum "CE685048S4QEI" {
        description
          "CE685048S4QEI chassis.";
      }
      enum "CE585048T4S2QEI" {
        description
          "CE585048T4S2QEI chassis.";
      }
      enum "CE685048T4QEI" {
        description
          "CE685048T4QEI chassis.";
      }
      enum "fname8090CX600-M8-AC" {
        description
          "CX600-M8-AC chassis.";
      }
      enum "fname8090CX600-M4" {
        description
          "CX600-M4 chassis.";
      }
      enum "fname8090CX600-M16" {
        description
          "CX600-M16 chassis.";
      }
      enum "fname8090CX600-X2-M8-AC" {
        description
          "CX600-X2-M8-AC chassis.";
      }
      enum "fname8031CX600-M2E" {
        description
          "CX600-M2E chassis.";
      }
      enum "fname8031CX600-M2F" {
        description
          "CX600-M2F chassis.";
      }
      enum "fname8090CX600-X1" {
        description
          "CX600-X1 chassis.";
      }
      enum "fname8090CX600-X2" {
        description
          "CX600-X2 chassis.";
      }
      enum "fname8090CX600-X1-M4" {
        description
          "CX600-X1-M4 chassis.";
      }
      enum "fname8090CX600-X2-M16" {
        description
          "CX600-X2-M16 chassis.";
      }
      enum "fname8090NE20E-X1" {
        description
          "NE20E-X1 chassis.";
      }
      enum "fname8090NE20E-X2" {
        description
          "NE20E-X2 chassis.";
      }
      enum "fname8090NE20E-X2-M8" {
        description
          "NE20E-X2-M8 chassis.";
      }
      enum "fname8090NE20E-X2-M16" {
        description
          "NE20E-X2-M16 chassis.";
      }
      enum "fnameNE20E-S2E" {
        description
          "NE20E-S2E chassis.";
      }
      enum "fnameNE20E-S2F" {
        description
          "NE20E-S2F chassis.";
      }
      enum "fname8090NE40E-X1" {
        description
          "NE40E-X1 chassis.";
      }
      enum "fname8090NE40E-X1-M4" {
        description
          "NE40E-X1-M4 chassis.";
      }
      enum "fname8090NE40E-X2" {
        description
          "NE40E-X2 chassis.";
      }
      enum "fname8090NE40E-M2E" {
        description
          "NE40E-M2E chassis.";
      }
      enum "fname8090NE40E-M2F" {
        description
          "NE40E-M2F chassis.";
      }
      enum "fname8090NE40E-X8" {
        description
          "NE40E-X8 chassis.";
      }
      enum "fname8090NE40E-X16" {
        description
          "NE40E-X16 chassis.";
      }
      enum "fname8090NE40E-X16A" {
        description
          "NE40E-X16A chassis.";
      }
      enum "fname8090NE40E-X16A-HVDC" {
        description
          "NE40E-X16A-HVDC chassis.";
      }
      enum "fname8090NE40E-X8A-HVDC" {
        description
          "NE40E-X8A-HVDC chassis.";
      }
      enum "fnameME60-X16A-HVDC" {
        description
          "ME60-X16A-HVDC chassis.";
      }
      enum "fnameME60-X8A-HVDC" {
        description
          "ME60-X8A-HVDC chassis.";
      }
      enum "fname8090CX600-X16A-HVDC" {
        description
          "CX600-X16A-HVDC chassis.";
      }
      enum "fname8090CX600-X8A-HVDC" {
        description
          "CX600-X8A-HVDC chassis.";
      }
      enum "fnamePTN6900-16A-HVDC" {
        description
          "PTN 6900-16A-HVDC chassis.";
      }
      enum "fnamePTN6900-8A-HVDC" {
        description
          "PTN 6900-8A-HVDC chassis.";
      }
      enum "fname8090CX600-X16A-DO-HVDC" {
        description
          "CX600-X16A-DO-HVDC chassis.";
      }
      enum "fname8090CX600-X8A-DO-HVDC" {
        description
          "CX600-X8A-DO-HVDC chassis.";
      }
      enum "fname8090NE40E-X16A-AC" {
        description
          "NE40E-X16A-AC chassis.";
      }
      enum "fname8090NE40E-X8A-AC" {
        description
          "NE40E-X8A-AC chassis.";
      }
      enum "fnameME60-X16A-AC" {
        description
          "ME60-X16A-AC chassis.";
      }
      enum "fnameME60-X8A-AC" {
        description
          "ME60-X8A-AC chassis.";
      }
      enum "fname8090CX600-X16A-AC" {
        description
          "CX600-X16A-AC chassis.";
      }
      enum "fname8090CX600-X8A-AC" {
        description
          "CX600-X8A-AC chassis.";
      }
      enum "fnamePTN6900-16A-AC" {
        description
          "PTN 6900-16A-AC chassis.";
      }
      enum "fnamePTN6900-8A-AC" {
        description
          "PTN 6900-8A-AC chassis.";
      }
      enum "fname8090CX600-X16A-DO-AC" {
        description
          "CX600-X16A-DO-AC chassis.";
      }
      enum "fname8090CX600-X8A-DO-AC" {
        description
          "CX600-X8A-DO-AC chassis.";
      }
      enum "fname8090NE40E-X16A-DC" {
        description
          "NE40E-X16A-DC chassis.";
      }
      enum "fname8090NE40E-X8A" {
        description
          "NE40E-X8A chassis.";
      }
      enum "fname8090NE40E-X8A-DC" {
        description
          "NE40E-X8A-DC chassis.";
      }
      enum "fname8090NE40E-X2-M8-AC" {
        description
          "NE40E-X2-M8-AC chassis.";
      }
      enum "fname8090NE40E-X2-M16" {
        description
          "NE40E-X2-M16 chassis.";
      }
      enum "fname8090NE20E-S4" {
        description
          "NE20E-S4 chassis.";
      }
      enum "fname8090NE20E-S8-AC" {
        description
          "NE20E-S8-AC chassis.";
      }
      enum "fname8090NE20E-S16" {
        description
          "NE20E-S16 chassis.";
      }
      enum "fname8090PTN6900-1-M4" {
        description
          "PTN 6900-1-M4 Chassis.";
      }
      enum "fname8090PTN6900-2-M8-AC" {
        description
          "PTN 6900-2-M8-AC Chassis.";
      }
      enum "fname8090PTN6900-2-M16" {
        description
          "PTN 6900-2-M16 Chassis.";
      }
      enum "fnamePTN6900-M2E" {
        description
          "PTN 6900-M2E chassis.";
      }
      enum "fnamePTN6900-M2F" {
        description
          "PTN 6900-M2F chassis.";
      }
      enum "fname8090NE40E-M2H" {
        description
          "NE40E-M2H chassis.";
      }
      enum "fname8031CX600-M2H" {
        description
          "CX600-M2H chassis.";
      }
      enum "fname8090CX600-X8" {
        description
          "CX600-X8 chassis.";
      }
      enum "fname8090CX600-X8A" {
        description
          "CX600-X8A chassis.";
      }
      enum "fname8090CX600-X8A-DC" {
        description
          "CX600-X8A-DC chassis.";
      }
      enum "fname8090CX600-X16" {
        description
          "CX600-X16 chassis.";
      }
      enum "fname8090CX600-X16A" {
        description
          "CX600-X16A chassis.";
      }
      enum "fname8090CX600-X16A-DC" {
        description
          "CX600-X16A-DC chassis.";
      }
      enum "fname8090NE5000E-X8" {
        description
          "NE5000EX8 Chassis.";
      }
      enum "fname8090NE9000-20" {
        description
          "NE9000-20 Chassis.";
      }
      enum "fnamePTN6900TNRK003BKP01" {
        description
          "PTN 6900-3 chassis.";
      }
      enum "fnamePTN6900TNRZ1BKPE" {
        description
          "PTN 6900-3-DC chassis.";
      }
      enum "fname8031CX6003AC" {
        description
          "CX600-X3 chassis.";
      }
      enum "fname8031CX6003DCDO" {
        description
          "CX600-X3-DC-DO chassis.";
      }
      enum "fname8031CX6003ACDO" {
        description
          "CX600-X3-AC-DO chassis.";
      }
      enum "fname8031CX600X8DO" {
        description
          "CX600-X8-DO chassis.";
      }
      enum "fname8031CX6003DC" {
        description
          "CX600-X3-DC chassis.";
      }
      enum "fname8090NE40E3AC" {
        description
          "NE40E-X3 chassis.";
      }
      enum "fname8090NE40E3DC" {
        description
          "NE40E-X3-DC chassis.";
      }
      enum "fnameME60-X3-AC" {
        description
          "ME60-X3 chassis.";
      }
      enum "fnameME60-X3-DC" {
        description
          "ME60-X3-DC chassis.";
      }
      enum "fnamePTN6900-3A" {
        description
          "PTN 6900-3A chassis.";
      }
      enum "fnameME60-X3A" {
        description
          "ME60-X3A chassis.";
      }
      enum "fname8090NE40E-X3A" {
        description
          "NE40E-X3A chassis.";
      }
      enum "fname8031CX600-X3A" {
        description
          "CX600-X3A chassis.";
      }
      enum "fnameME60-X8" {
        description
          "ME60-X8 chassis.";
      }
      enum "fnameME60-X16" {
        description
          "ME60-X16 chassis.";
      }
      enum "fnameME60-X8A" {
        description
          "ME60-X8A chassis.";
      }
      enum "fnameME60-X8A-DC" {
        description
          "ME60-X8A-DC chassis.";
      }
      enum "fnameME60-X16A" {
        description
          "ME60-X16A chassis.";
      }
      enum "fnameME60-X16A-DC" {
        description
          "ME60-X16A-DC chassis.";
      }
      enum "fnamePTN6900Half" {
        description
          "PTN 6900-8 chassis.";
      }
      enum "fnamePTN6900Whole" {
        description
          "PTN 6900-16 chassis.";
      }
      enum "fnamePTN6900-8A" {
        description
          "PTN 6900-8A chassis.";
      }
      enum "fnamePTN6900-8A-DC" {
        description
          "PTN 6900-8A-DC chassis.";
      }
      enum "fnamePTN6900-16A" {
        description
          "PTN 6900-16A chassis.";
      }
      enum "fnamePTN6900-16A-DC" {
        description
          "PTN 6900-16A-DC chassis.";
      }
      enum "fname8090CX600-X8A-DO" {
        description
          "CX600-X8A-DO chassis.";
      }
      enum "fname8090CX600-X8A-DO-DC" {
        description
          "CX600-X8A-DO-DC chassis.";
      }
      enum "fname8090CX600-X16A-DO" {
        description
          "CX600-X16A-DO chassis.";
      }
      enum "fname8090CX600-X16A-DO-DC" {
        description
          "CX600-X16A-DO-DC chassis.";
      }
      enum "fname8090CX600-X16-DO" {
        description
          "CX600-X16-DO chassis.";
      }
      enum "fname8031CX600-X3A-DO" {
        description
          "CX600-X3A-DO chassis.";
      }
      enum "fname8090CX600-X2-M8A-AC" {
        description
          "CX600-X2-M8A-AC chassis.";
      }
      enum "fname8090CX600-X2-M8A-DC" {
        description
          "CX600-X2-M8A-DC chassis.";
      }
      enum "fname8031CX600-M8ADO" {
        description
          "CX600-M8ADO chassis.";
      }
      enum "fname8031CX600-M8ADO-DC" {
        description
          "CX600-M8ADO-DC chassis.";
      }
      enum "fname8090NE20E-S8A-AC" {
        description
          "NE20E-S8A-AC chassis.";
      }
      enum "fname8090NE20E-S8A-DC" {
        description
          "NE20E-S8A-DC chassis.";
      }
      enum "fname8090NE40E-X2-M8A-AC" {
        description
          "NE40E-X2-M8A-AC chassis.";
      }
      enum "fname8090NE40E-X2-M8A-DC" {
        description
          "NE40E-X2-M8A-DC chassis.";
      }
      enum "fname8090PTN6900-2-M8A-AC" {
        description
          "PTN 6900-2-M8A-AC chassis.";
      }
      enum "fname8090PTN6900-2-M8A-DC" {
        description
          "PTN 6900-2-M8A-DC chassis.";
      }
      enum "fnameME60-X2-M8A-AC" {
        description
          "ME60-X2-M8A-AC chassis.";
      }
      enum "fnameME60-X2-M8A-DC" {
        description
          "ME60-X2-M8A-DC chassis.";
      }
      enum "fname8090CX600-X2-M16A" {
        description
          "CX600-X2-M16A chassis.";
      }
      enum "fname8031CX600-M16ADO" {
        description
          "CX600-M16ADO chassis.";
      }
      enum "fname8090NE20E-S16A" {
        description
          "NE20E-S16A chassis.";
      }
      enum "fname8090NE40E-X2-M16A" {
        description
          "NE40E-X2-M16A chassis.";
      }
      enum "fname8090PTN6900-2-M16A" {
        description
          "PTN 6900-2-M16A chassis.";
      }
      enum "fnameME60-X2-M16A" {
        description
          "ME60-X2-M16A chassis.";
      }
      enum "fname8090CX600-M8-DC" {
        description
          "CX600-M8-DC chassis.";
      }
      enum "fname8090CX600-X2-M8-DC" {
        description
          "CX600-X2-M8-DC chassis.";
      }
      enum "fname8090NE40E-X2-M8-DC" {
        description
          "NE40E-X2-M8-DC chassis.";
      }
      enum "fname8090NE20E-S8-DC" {
        description
          "NE20E-S8-DC chassis.";
      }
      enum "fname8090PTN6900-2-M8-DC" {
        description
          "PTN 6900-2-M8-DC Chassis.";
      }
      enum "fnameME60-X2-M8-AC" {
        description
          "ME60-X2-M8-AC chassis.";
      }
      enum "fnameME60-X2-M8-DC" {
        description
          "ME60-X2-M8-DC chassis.";
      }
      enum "fnameME60-X2-M16" {
        description
          "ME60-X2-M16 chassis.";
      }
    }
    description
      "";
  }
  typedef devmChassisSvcType {
    type enumeration {
      enum "unknown" {
        description
          "Unknown.";
      }
      enum "other" {
        description
          "Other.";
      }
      enum "centralChassis" {
        description
          "Cluster central chassis.";
      }
      enum "lineChassis" {
        description
          "Cluster line chassis.";
      }
    }
    description
      "";
  }
  typedef devmBoardType {
    type enumeration {
      enum "unknown" {
        description
          "Unknown device.";
      }
      enum "CX6D00MPUD11" {
        description
          "CX6D00MPUD11.";
      }
      enum "CX6D0SRUA611" {
        description
          "CX6D0SRUA611.";
      }
      enum "CX6DSFUIA07C" {
        description
          "CX6DSFUIA07C.";
      }
      enum "CX6DL2XEIG1B" {
        description
          "CX6DL2XEIG1B.";
      }
      enum "CX6DL4XEBG1B" {
        description
          "CX6DL4XEBG1B.";
      }
      enum "CX6D0L5XFA11" {
        description
          "CX6D0L5XFA11.";
      }
      enum "CR5D0EFGFA73" {
        description
          "CR5D0EFGFA73.";
      }
      enum "CR5DL1XEDG70" {
        description
          "CR5DL1XEDG70.";
      }
      enum "CX6D0LAXFA11" {
        description
          "CX6D0LAXFA11.";
      }
      enum "CX6DISUF5010" {
        description
          "CX6DISUF5010.";
      }
      enum "CR5DLPUF5071" {
        description
          "CR5DLPUF5071.";
      }
      enum "CR5DLPUF507M" {
        description
          "CR5DLPUF507M.";
      }
      enum "CX6DISUF5011" {
        description
          "CX6DISUF5011.";
      }
      enum "CX6DL1XEDG1A" {
        description
          "CX6DL1XEDG1A.";
      }
      enum "CX6D0EFGFA12" {
        description
          "CX6D0EFGFA12.";
      }
      enum "CX6D0EMGFA10" {
        description
          "CX6D0EMGFA10.";
      }
      enum "ME0DMSUFF070" {
        description
          "ME0DMSUFF070.";
      }
      enum "CR5D00E2NC76" {
        description
          "CR5D00E2NC76.";
      }
      enum "CR5D00LEXF76" {
        description
          "CR5D00LEXF76.";
      }
      enum "CR5DE1NLAX76" {
        description
          "CR5DE1NLAX76.";
      }
      enum "CR5D00E2NC75" {
        description
          "CR5D00E2NC75.";
      }
      enum "CR5D00LEXF75" {
        description
          "CR5D00LEXF75.";
      }
      enum "CR5DLPUFE07B" {
        description
          "CR5DLPUFE07B.";
      }
      enum "CR5DE1NLAX75" {
        description
          "CR5DE1NLAX75.";
      }
      enum "CR5D0E6MFA70" {
        description
          "CR5D0E6MFA70.";
      }
      enum "CR5D0E6MFA71" {
        description
          "CR5D0E6MFA71.";
      }
      enum "CR52MPUA" {
        description
          "CR52MPUA.";
      }
      enum "CR52MPUB" {
        description
          "CR52MPUB.";
      }
      enum "CR55MPUA" {
        description
          "CR55MPUA.";
      }
      enum "CR55MPUAB" {
        description
          "CR55MPUAB.";
      }
      enum "CR56RPUA" {
        description
          "CR56RPUA.";
      }
      enum "CR52LPUA" {
        description
          "CR52LPUA.";
      }
      enum "CR52LPUB" {
        description
          "CR52LPUB.";
      }
      enum "CR52LPUC" {
        description
          "CR52LPUC.";
      }
      enum "CR52LPUE" {
        description
          "CR52LPUE.";
      }
      enum "CR52LPUR" {
        description
          "CR52LPUR.";
      }
      enum "CR52LPUF" {
        description
          "CR52LPUF.";
      }
      enum "CR52LPUG" {
        description
          "CR52LPUG.";
      }
      enum "CR52LPUH" {
        description
          "CR52LPUH.";
      }
      enum "CR52LPUI" {
        description
          "CR52LPUI.";
      }
      enum "CR52LPUK" {
        description
          "CR52LPUK.";
      }
      enum "CR52LPUM" {
        description
          "CR52LPUM.";
      }
      enum "CR52LPUN" {
        description
          "CR52LPUN.";
      }
      enum "CR52SPUC" {
        description
          "CR52SPUC.";
      }
      enum "CR56LPUF100A" {
        description
          "CR56LPUF100A.";
      }
      enum "CR56LPUF100B" {
        description
          "CR56LPUF100B.";
      }
      enum "CR56LPUI100A" {
        description
          "CR56LPUI100A.";
      }
      enum "CR56LPUI100B" {
        description
          "CR56LPUI100B.";
      }
      enum "CR56LPUI100C" {
        description
          "CR56LPUI100C.";
      }
      enum "CR56LPUF200A" {
        description
          "CR56LPUF200A.";
      }
      enum "CR52SFUA" {
        description
          "CR52SFUA.";
      }
      enum "CR52SRUA" {
        description
          "CR52SRUA.";
      }
      enum "CR52SFUD" {
        description
          "CR52SFUD.";
      }
      enum "CR52SFUF" {
        description
          "CR52SFUF.";
      }
      enum "CR52SFUG" {
        description
          "CR52SFUG.";
      }
      enum "CR52SFUC" {
        description
          "CR52SFUC.";
      }
      enum "CR52SFEA" {
        description
          "CR52SFEA.";
      }
      enum "CR52K-SFEA" {
        description
          "CR52K-SFEA.";
      }
      enum "CR55SFUA" {
        description
          "CR55SFUA.";
      }
      enum "CR55ECUA" {
        description
          "CR55ECUA.";
      }
      enum "CR55C-ECUA" {
        description
          "CR55C-ECUA.";
      }
      enum "CR55ICUA" {
        description
          "CR55ICUA.";
      }
      enum "CR56SFUF100B" {
        description
          "CR56SFUF100B.";
      }
      enum "CR55SFUI100A" {
        description
          "CR55SFUI100A.";
      }
      enum "CR55ECU100A" {
        description
          "CR55ECU100A.";
      }
      enum "CR52SFEB" {
        description
          "CR52SFEB.";
      }
      enum "CR56SFUF100C" {
        description
          "CR56SFUF100C.";
      }
      enum "CR56SFU200A" {
        description
          "CR56SFU200A.";
      }
      enum "CR5D00EKGF60" {
        description
          "CR5D00EKGF60.";
      }
      enum "CR5D00P4XX60" {
        description
          "CR5D00P4XX60.";
      }
      enum "CR5D00P8UF61" {
        description
          "CR5D00P8UF61.";
      }
      enum "CR5D00E4XX60" {
        description
          "CR5D00E4XX60.";
      }
      enum "CR5D00W4XX60" {
        description
          "CR5D00W4XX60.";
      }
      enum "CR5DLPUFA060" {
        description
          "CR5DLPUFA060.";
      }
      enum "CR5D00LEXF60" {
        description
          "CR5D00LEXF60.";
      }
      enum "CR5D00E2NC60" {
        description
          "CR5D00E2NC60.";
      }
      enum "CR5DE1NLAX60" {
        description
          "CR5DE1NLAX60.";
      }
      enum "CR5D00E1NC60" {
        description
          "CR5D00E1NC60.";
      }
      enum "CR5D00LAXX60" {
        description
          "CR5D00LAXX60.";
      }
      enum "CR5DSFEBA06B" {
        description
          "CR5DSFEBA06B.";
      }
      enum "CR5D0MPUB461" {
        description
          "CR5D0MPUB461.";
      }
      enum "CR5DSFUFA06B" {
        description
          "CR5DSFUFA06B.";
      }
      enum "CR5DSFUIE060" {
        description
          "CR5DSFUIE060.";
      }
      enum "CR5DSFUFA06C" {
        description
          "CR5DSFUFA06C.";
      }
      enum "CR5D0MPUA450" {
        description
          "CR5D0MPUA450.";
      }
      enum "CR5DECUFA050" {
        description
          "CR5DECUFA050.";
      }
      enum "CR5DSFUIA050" {
        description
          "CR5DSFUIA050.";
      }
      enum "CX6D00MPUK70" {
        description
          "CX6D00MPUK70.";
      }
      enum "CX6PM2EBAS70" {
        description
          "CX6PM2EBAS70.";
      }
      enum "CX6PM2EBAS71" {
        description
          "CX6PM2EBAS71.";
      }
      enum "CX6PM2FBAS70" {
        description
          "CX6PM2FBAS70.";
      }
      enum "CX6PM2FBAS71" {
        description
          "CX6PM2FBAS71.";
      }
      enum "CR2P2EBASD10" {
        description
          "CR2P2EBASD10.";
      }
      enum "CR2P2EBASA10" {
        description
          "CR2P2EBASA10.";
      }
      enum "CR2P2FBASD10" {
        description
          "CR2P2FBASD10.";
      }
      enum "CR2P2FBASA10" {
        description
          "CR2P2FBASA10.";
      }
      enum "CR5PM2EBAS70" {
        description
          "CR5PM2EBAS70.";
      }
      enum "CR5PM2EBAS71" {
        description
          "CR5PM2EBAS71.";
      }
      enum "CR5PM2FBAS70" {
        description
          "CR5PM2FBAS70.";
      }
      enum "CR5PM2FBAS71" {
        description
          "CR5PM2FBAS71.";
      }
      enum "TNRPM2EBAS70" {
        description
          "TNRPM2EBAS70.";
      }
      enum "TNRPM2EBAS71" {
        description
          "TNRPM2EBAS71.";
      }
      enum "TNRPM2FBAS70" {
        description
          "TNRPM2FBAS70.";
      }
      enum "TNRPM2FBAS71" {
        description
          "TNRPM2FBAS71.";
      }
      enum "CR5PM2HBAS72" {
        description
          "CR5PM2HBAS72.";
      }
      enum "CR5PM2HBAS73" {
        description
          "CR5PM2HBAS73.";
      }
      enum "CR5B0BKP0377" {
        description
          "CR5B0BKP0377.";
      }
      enum "CX6PM2HBAS72" {
        description
          "CX6PM2HBAS72.";
      }
      enum "CX6PM2HBAS73" {
        description
          "CX6PM2HBAS73.";
      }
      enum "CX6B0BKP0375" {
        description
          "CX6B0BKP0375.";
      }
      enum "CX6D00MPUK10" {
        description
          "CX6D00MPUK10.";
      }
      enum "CR5D00MPUK70" {
        description
          "CR5D00MPUK70.";
      }
      enum "CR2D00MPUE10" {
        description
          "CR2D00MPUE10.";
      }
      enum "TNRD00MPUK70" {
        description
          "TNRD00MPUK70.";
      }
      enum "CR5D0NPU5070" {
        description
          "CR5D0NPU5070.";
      }
      enum "CX6D0NSU5010" {
        description
          "CX6D0NSU5010.";
      }
      enum "CR2D0NSP5010" {
        description
          "CR2D0NSP5010.";
      }
      enum "CR5DNPU50E70" {
        description
          "CR5DNPU50E70.";
      }
      enum "CR2DNSPE5010" {
        description
          "CR2DNSPE5010.";
      }
      enum "CX6X0PWRDC70" {
        description
          "CX6X0PWRDC70.";
      }
      enum "CX6M001FBX71" {
        description
          "CX6M001FBX71.";
      }
      enum "CX6M002FBX72" {
        description
          "CX6M002FBX72.";
      }
      enum "CX6M002FBX73" {
        description
          "CX6M002FBX73.";
      }
      enum "CX6DNPUI120" {
        description
          "CR5D0NPU120.";
      }
      enum "CR5DNPU12070" {
        description
          "CR5DNPU12070.";
      }
      enum "CX6DNSU12010" {
        description
          "CX6DNSU12010.";
      }
      enum "CR2DNSP12010" {
        description
          "CR2DNSP12010.";
      }
      enum "CR5DNPU1207E" {
        description
          "CR5DNPU1207E.";
      }
      enum "CR2DNSP1201E" {
        description
          "CR2DNSP1201E.";
      }
      enum "CLOCK" {
        description
          "CLOCK.";
      }
      enum "EXTPOWER" {
        description
          "EXTPOWER.";
      }
      enum "POWER" {
        description
          "POWER.";
      }
      enum "POWER DC" {
        description
          "POWER DC.";
      }
      enum "POWER AC" {
        description
          "POWER AC.";
      }
      enum "FAN" {
        description
          "FAN.";
      }
      enum "CX67FCBA" {
        description
          "FAN.";
      }
      enum "CX67FCBB" {
        description
          "FAN.";
      }
      enum "CX67FCBB_R" {
        description
          "FAN.";
      }
      enum "CX68FCBC" {
        description
          "FAN.";
      }
      enum "CX68FCBC_NEW" {
        description
          "FAN.";
      }
      enum "CX68FCBD" {
        description
          "FAN.";
      }
      enum "CX68FCBD_R" {
        description
          "FAN.";
      }
      enum "LCD" {
        description
          "LCD.";
      }
      enum "PMU" {
        description
          "PMU.";
      }
      enum "PM" {
        description
          "PM.";
      }
      enum "DE51SRU1A" {
        description
          "DE51SRU1A.";
      }
      enum "DE51SRU1B" {
        description
          "DE51SRU1B.";
      }
      enum "DE51SRU1C" {
        description
          "DE51SRU1C.";
      }
      enum "CR5DSFUIK06A" {
        description
          "CR5DSFUIK06A.";
      }
      enum "CR5D0MPUA550" {
        description
          "CR5D0MPUA550.";
      }
      enum "CR5D00ICUB50" {
        description
          "CR5D00ICUB50.";
      }
      enum "CR5DSFUFK050" {
        description
          "CR5DSFUFK050.";
      }
      enum "CR5D0MPUA451" {
        description
          "CR5D0MPUA451.";
      }
      enum "CR5D00ICUA51" {
        description
          "CR5D00ICUA51.";
      }
      enum "CR5DSFUFK051" {
        description
          "CR5DSFUFK051.";
      }
      enum "CR5DSFUFT050" {
        description
          "CR5DSFUFT050.";
      }
      enum "CR5DSFUIT06H" {
        description
          "CR5DSFUIT06H.";
      }
      enum "CR5D0MPUA750" {
        description
          "CR5D0MPUA750.";
      }
      enum "CR5D0MPUB660" {
        description
          "CR5D0MPUB660.";
      }
      enum "CR5DSFUIK06B" {
        description
          "CR5DSFUIK06B.";
      }
      enum "CR5DSFUIK06C" {
        description
          "CR5DSFUIK06C.";
      }
      enum "CR9D0MPUN180" {
        description
          "CR9D0MPUN180.";
      }
      enum "CR9D00E8NC80" {
        description
          "CR9D00E8NC80.";
      }
      enum "CR9D00EFMB80" {
        description
          "CR9D00EFMB80.";
      }
      enum "CR9D0SFUTF80" {
        description
          "CR9D0SFUTF80.";
      }
      enum "CR9D00EPXF80" {
        description
          "CR9D00EPXF80.";
      }
      enum "CR9D00EDNB80" {
        description
          "CR9D00EDNB80.";
      }
      enum "CR9D000CMU60" {
        description
          "CR9D000CMU60.";
      }
      enum "CR9D00D8NC80" {
        description
          "CR9D00D8NC80.";
      }
      enum "CR5DLPUFK061" {
        description
          "CR5DLPUFK061.";
      }
      enum "CR5D00LMXF61" {
        description
          "CR5D00LMXF61.";
      }
      enum "CR5D00LAXF60" {
        description
          "CR5D00LAXF60.";
      }
      enum "CR5D0MPUB560" {
        description
          "CR5D0MPUB560.";
      }
      enum "CR57LPUF120A" {
        description
          "CR57LPUF120A.";
      }
      enum "CR57LPUF240A" {
        description
          "CR57LPUF240A.";
      }
      enum "CR57LPUF480B" {
        description
          "CR57LPUF480B.";
      }
      enum "CR57SRU200A" {
        description
          "CR57SRU200A.";
      }
      enum "CR57SFU200C" {
        description
          "CR57SFU200C.";
      }
      enum "CR57FRA200A" {
        description
          "CR57FRA200A.";
      }
      enum "CR57SFU200B" {
        description
          "CR57SFU200B.";
      }
      enum "CR5DLPUFB070" {
        description
          "CR5DLPUFB070.";
      }
      enum "CR5DLPUFB07B" {
        description
          "CR5DLPUFB07B.";
      }
      enum "CR5DLPUFF070" {
        description
          "CR5DLPUFF070.";
      }
      enum "CR5DLPUFF080" {
        description
          "CR5DLPUFF080.";
      }
      enum "CR5DLPUFF07B" {
        description
          "CR5DLPUFF07B.";
      }
      enum "CR5DSFUIE07B" {
        description
          "CR5DSFUIE07B.";
      }
      enum "CR5DSFUIE07D" {
        description
          "CR5DSFUIE07D.";
      }
      enum "CR5D0MPUB570" {
        description
          "CR5D0MPUB570.";
      }
      enum "CX6D0MPUB570" {
        description
          "CX6D0MPUB570.";
      }
      enum "CR5D0SRUA970" {
        description
          "CR5D0SRUA970.";
      }
      enum "CR5D0SRUA870" {
        description
          "CR5D0SRUA870.";
      }
      enum "CX6D0SRUA970" {
        description
          "CX6D0SRUA970.";
      }
      enum "CX6D0SRUA870" {
        description
          "CX6D0SRUA870.";
      }
      enum "CR5D00E8NC70" {
        description
          "CR5D00E8NC70.";
      }
      enum "CR5D00E8NC7B" {
        description
          "CR5D00E8NC7B.";
      }
      enum "CR5DLPUF517E" {
        description
          "CR5DLPUF517E.";
      }
      enum "CR5D0EMGFA7J" {
        description
          "CR5D0EMGFA7J.";
      }
      enum "CR5DL2XEFG7J" {
        description
          "CR5DL2XEFG7J.";
      }
      enum "CR5DSFUIU07C" {
        description
          "CR5DSFUIU07C.";
      }
      enum "CR5DSFUIM07C" {
        description
          "CR5DSFUIM07C.";
      }
      enum "CX6DSFUIU07C" {
        description
          "CX6DSFUIU07C.";
      }
      enum "CX6DSFUIM07C" {
        description
          "CX6DSFUIM07C.";
      }
      enum "CR5DSFUIU07B" {
        description
          "CR5DSFUIU07B.";
      }
      enum "CR5DSFUIM07B" {
        description
          "CR5DSFUIM07B.";
      }
      enum "CX6DSFUIU07B" {
        description
          "CX6DSFUIU07B.";
      }
      enum "CX6DSFUIM07B" {
        description
          "CX6DSFUIM07B.";
      }
      enum "CR57FRA1TA" {
        description
          "CR57FRA1TA.";
      }
      enum "CR5D0LBXFA70" {
        description
          "CR5D0LBXFA70.";
      }
      enum "CR5D0E2MCA70" {
        description
          "CR5D0E2MCA70.";
      }
      enum "CR5D00E1NC76" {
        description
          "CR5D00E1NC76.";
      }
      enum "CR5D00E1NC78" {
        description
          "CR5D00E1NC78.";
      }
      enum "CR5D0LBXFA7B" {
        description
          "CR5D0LBXFA7B.";
      }
      enum "CR5D0E2MCA7B" {
        description
          "CR5D0E2MCA7B.";
      }
      enum "CR5D00E1NC7B" {
        description
          "CR5D00E1NC7B.";
      }
      enum "CR5D00E1NC7C" {
        description
          "CR5D00E1NC7C.";
      }
      enum "CR5D00E2NC70" {
        description
          "CR5D00E2NC70.";
      }
      enum "CR5D00E2NC71" {
        description
          "CR5D00E2NC71.";
      }
      enum "CR5D00LFXF70" {
        description
          "CR5D00LFXF70.";
      }
      enum "CR5DE2NLBX70" {
        description
          "CR5DE2NLBX70.";
      }
      enum "CR5DE1NLBX70" {
        description
          "CR5DE1NLBX70.";
      }
      enum "CR5D00E2NC73" {
        description
          "CR5D00E2NC73.";
      }
      enum "CR5D00E2NC74" {
        description
          "CR5D00E2NC74.";
      }
      enum "CR5D00LFXF73" {
        description
          "CR5D00LFXF73.";
      }
      enum "CR5DE2NLBX73" {
        description
          "CR5DE2NLBX73.";
      }
      enum "CR5DE1NLBX71" {
        description
          "CR5DE1NLBX71.";
      }
      enum "CR5DSFUIE07C" {
        description
          "CR5DSFUIE07C.";
      }
      enum "CX6DSFUIE01C" {
        description
          "CX6DSFUIE01C.";
      }
      enum "CR5D0SRUA570" {
        description
          "CR5D0SRUA570.";
      }
      enum "CX6D0SRUA510" {
        description
          "CX6D0SRUA510.";
      }
      enum "CR5D0MPUB460" {
        description
          "CR5D0MPUB460.";
      }
      enum "CX6D0MPUB410" {
        description
          "CX6D0MPUB410.";
      }
      enum "CR5DLPUFM070" {
        description
          "CR5DLPUFM070.";
      }
      enum "CR5D00LMXF70" {
        description
          "CR5D00LMXF70.";
      }
      enum "CR5DE2NLFX70" {
        description
          "CR5DE2NLFX70.";
      }
      enum "CR5D00E4NC70" {
        description
          "CR5D00E4NC70.";
      }
      enum "CR5D00D4NC70" {
        description
          "CR5D00D4NC70.";
      }
      enum "CR5D00D8NC70" {
        description
          "CR5D00D8NC70.";
      }
      enum "CR5DLPUFME70" {
        description
          "CR5DLPUFME70.";
      }
      enum "ME0DBSUFM070" {
        description
          "ME0DBSUFM070.";
      }
      enum "ME0DMSUFM070" {
        description
          "ME0DMSUFM070.";
      }
      enum "CX6DSFUIE01B" {
        description
          "CX6DSFUIE01B.";
      }
      enum "fname8090CX600-X8" {
        description
          "fname8090CX600-X8.";
      }
      enum "fname8090CX600-X16" {
        description
          "fname8090CX600-X16.";
      }
      enum "CR5DSFUIT060" {
        description
          "CR5DSFUIT060.";
      }
      enum "CR5DSFUIT06E" {
        description
          "CR5DSFUIT06E.";
      }
      enum "CR5DSFUIT26A" {
        description
          "CR5DSFUIT26A.";
      }
      enum "CR5D00E8NC61" {
        description
          "CR5D00E8NC61.";
      }
      enum "CR5DE8NEDX61" {
        description
          "CR5DE8NEDX61";
      }
      enum "CR5D00EDNB60" {
        description
          "CR5D00EDNB60.";
      }
      enum "CR5DEDNLIX60" {
        description
          "CR5DEDNLIX60.";
      }
      enum "CR5DLPUFT060" {
        description
          "CR5DLPUFT060.";
      }
      enum "CR5D00EFMB60" {
        description
          "CR5D00EFMB60.";
      }
      enum "CR5D00E8NC60" {
        description
          "CR5D00E8NC60.";
      }
      enum "CR5DSFU0K06B" {
        description
          "CR5DSFU0K06B.";
      }
      enum "CR5D0SRUB060" {
        description
          "CR5D0SRUB060.";
      }
      enum "CR56SRUB1TA" {
        description
          "CR56SRUB1TA.";
      }
      enum "CR5D0SFUT061" {
        description
          "CR5D0SFUT061.";
      }
      enum "CR56SFU1TC" {
        description
          "CR56SFU1TC.";
      }
      enum "CR56FRA1TA" {
        description
          "CR56FRA1TA.";
      }
      enum "CR5D0MPUC061" {
        description
          "CR5D0MPUC061.";
      }
      enum "CR5DLPUFK062" {
        description
          "CR5DLPUFK062.";
      }
      enum "CR5D00L4NC60" {
        description
          "CR5D00L4NC60.";
      }
      enum "CR5D00LKXF60" {
        description
          "CR5D00LKXF60.";
      }
      enum "CR5DL2NLEX60" {
        description
          "CR5DL2NLEX60.";
      }
      enum "CR5DNPU24070" {
        description
          "CR5DNPU24070.";
      }
      enum "CR5DNPU24071" {
        description
          "CR5DNPU24071.";
      }
      enum "CR2DNSPA0010" {
        description
          "CR2DNSPA0010.";
      }
      enum "CR2DNSPB0010" {
        description
          "CR2DNSPB0010.";
      }
      enum "CR5DNPU48070" {
        description
          "CR5DNPU48070.";
      }
      enum "CR2DNSPC0010" {
        description
          "CR2DNSPC0010.";
      }
      enum "CX6D0MPUK170" {
        description
          "CX6D0MPUK170.";
      }
      enum "ME0D0MPUK171" {
        description
          "ME0D0MPUK171.";
      }
      enum "CR5D0MPUK170" {
        description
          "CR5D0MPUK170.";
      }
      enum "TNUD00MPUK71" {
        description
          "TNUD00MPUK71.";
      }
      enum "CR2D0MPUE110" {
        description
          "CR2D0MPUE110.";
      }
      enum "CR5DLPUF5070" {
        description
          "CR5DLPUF5070.";
      }
      enum "CR5DLPUF5170" {
        description
          "CR5DLPUF5170.";
      }
      enum "CR5DLPUF517B" {
        description
          "CR5DLPUF517B.";
      }
      enum "CR5D0L5XFA71" {
        description
          "CR5D0L5XFA71.";
      }
      enum "CR5D0L4XFA70" {
        description
          "CR5D0L4XFA70.";
      }
      enum "CR5D0EMGFA70" {
        description
          "CR5D0EMGFA70.";
      }
      enum "CR5DL2XEFG7A" {
        description
          "CR5DL2XEFG7A.";
      }
      enum "CR5DL3XEFG7C" {
        description
          "CR5DL3XEFG7C.";
      }
      enum "CR5D0L5XFA7B" {
        description
          "CR5D0L5XFA7B.";
      }
      enum "CR5D0L4XFA7B" {
        description
          "CR5D0L4XFA7B.";
      }
      enum "CR5D0EMGFA7B" {
        description
          "CR5D0EMGFA7B.";
      }
      enum "CR5DL2XEFG7B" {
        description
          "CR5DL2XEFG7B.";
      }
      enum "CR5D00L5XF72" {
        description
          "CR5D00L5XF72.";
      }
      enum "CR5D00L4XF71" {
        description
          "CR5D00L4XF71.";
      }
      enum "CR5D00EMGF73" {
        description
          "CR5D00EMGF73.";
      }
      enum "CR5DL2XEFG72" {
        description
          "CR5DL2XEFG72.";
      }
      enum "CR5D0L5XFA7L" {
        description
          "CR5D0L5XFA7L.";
      }
      enum "CR5DL2XEIG7L" {
        description
          "CR5DL2XEIG7L.";
      }
      enum "CR5D0EMGFA7L" {
        description
          "CR5D0EMGFA7L.";
      }
      enum "CR5DLPUFA071" {
        description
          "CR5DLPUFA071.";
      }
      enum "CR5DLPUFA07B" {
        description
          "CR5DLPUFA07B.";
      }
      enum "CR5D00E2MC70" {
        description
          "CR5D00E2MC70.";
      }
      enum "CR5D0LAXFA71" {
        description
          "CR5D0LAXFA71.";
      }
      enum "CR5D00E1NC72" {
        description
          "CR5D00E1NC72.";
      }
      enum "CR5D00E2MC7B" {
        description
          "CR5D00E2MC7B.";
      }
      enum "CR5D0LAXFA7B" {
        description
          "CR5D0LAXFA7B.";
      }
      enum "CR5D00E2MC71" {
        description
          "CR5D00E2MC71.";
      }
      enum "CR5D0LAXFA72" {
        description
          "CR5D0LAXFA72.";
      }
      enum "CR5D00E1NC73" {
        description
          "CR5D00E1NC73.";
      }
      enum "ME0DBSUFA070" {
        description
          "ME0DBSUFA070.";
      }
      enum "ME0DBSUFF070" {
        description
          "ME0DBSUFF070.";
      }
      enum "CR5DLPUFB07E" {
        description
          "CR5DLPUFB07E.";
      }
      enum "CR5DLPUFF07E" {
        description
          "CR5DLPUFF07E.";
      }
      enum "ME0DMSUFA070" {
        description
          "ME0DMSUFA070.";
      }
      enum "ME0DMSUF5170" {
        description
          "ME0DMSUF5170.";
      }
      enum "ME0DBSUF5170" {
        description
          "ME0DBSUF5170.";
      }
      enum "CR5DLPUF507L" {
        description
          "CR5DLPUF507L.";
      }
      enum "CR5DL4XEBG7L" {
        description
          "CR5DL4XEBG7L.";
      }
      enum "CR5D0L5XFA7J" {
        description
          "CR5D0L5XFA7J.";
      }
      enum "CR5D00LBXF7L" {
        description
          "CR5D00LBXF7L.";
      }
      enum "CR5D00L5XF73" {
        description
          "CR5D00L5XF73.";
      }
      enum "CR5D00EMGF74" {
        description
          "CR5D00EMGF74.";
      }
      enum "CR5DL2XEFG73" {
        description
          "CR5DL2XEFG73.";
      }
      enum "CR5DLPUFA07J" {
        description
          "CR5DLPUFA07J.";
      }
      enum "CR5DLPUFA27E" {
        description
          "CR5DLPUFA27E.";
      }
      enum "CR5D00LFXF7L" {
        description
          "CR5D00LFXF7L.";
      }
      enum "CR5D00TBXF71" {
        description
          "CR5D00TBXF71.";
      }
      enum "CR5D00TFXF71" {
        description
          "CR5D00TFXF71.";
      }
      enum "CR5D0MPUD170" {
        description
          "CR5D0MPUD170.";
      }
      enum "CR5D0MPUD270" {
        description
          "CR5D0MPUD270.";
      }
      enum "CX6D0MPUD170" {
        description
          "CX6D0MPUD170.";
      }
      enum "CX6D0MPUD270" {
        description
          "CX6D0MPUD270.";
      }
      enum "TNRD0MPUD270" {
        description
          "TNRD0MPUD270.";
      }
      enum "TNRD0MPUD370" {
        description
          "TNRD0MPUD370.";
      }
      enum "ME0D00MPUD71" {
        description
          "ME0D00MPUD71.";
      }
      enum "ME0D00MPUD72" {
        description
          "ME0D00MPUD72.";
      }
      enum "CR5D0MPUD470" {
        description
          "CR5D0MPUD470.";
      }
      enum "CX6D0MPUD470" {
        description
          "CX6D0MPUD470.";
      }
      enum "TNRD0MPUD470" {
        description
          "TNRD0MPUD470.";
      }
      enum "ME0P0MPUD470" {
        description
          "ME0P0MPUD470.";
      }
      enum "CR5D00D2NT70" {
        description
          "CR5D00D2NT70.";
      }
      enum "CR5DLPUFE070" {
        description
          "CR5DLPUFE070.";
      }
      enum "TNRD0SRUA870" {
        description
          "TNRD0SRUA870.";
      }
      enum "TNRDSFUIM07C" {
        description
          "TNRDSFUIM07C.";
      }
      enum "TNRD0SRUA970" {
        description
          "TNRD0SRUA970.";
      }
      enum "TNRDSFUIU07C" {
        description
          "TNRDSFUIU07C.";
      }
      enum "ME0D0SRUA870" {
        description
          "ME0D0SRUA870.";
      }
      enum "ME0D0SRUA970" {
        description
          "ME0D0SRUA970.";
      }
      enum "ME0DSFUIU07C" {
        description
          "ME0DSFUIU07C.";
      }
      enum "ME0DSFUIK07B" {
        description
          "ME0DSFUIK07B.";
      }
      enum "TNRD0MPUB470" {
        description
          "TNRD0MPUB470.";
      }
      enum "TNRD0MPUB570" {
        description
          "TNRD0MPUB570.";
      }
      enum "TNRDSFUIE07B" {
        description
          "TNRDSFUIE07B.";
      }
      enum "ME0D0MPUB570" {
        description
          "ME0D0MPUB570.";
      }
      enum "ME0DSFUIE07B" {
        description
          "ME0DSFUIE07B.";
      }
      enum "TNRD0SRUA570" {
        description
          "TNRD0SRUA570.";
      }
      enum "TNRDSFUIE07C" {
        description
          "TNRDSFUIE07C.";
      }
      enum "TNRDSFUIM07B" {
        description
          "TNRDSFUIM07B.";
      }
      enum "TNRDSFUIU07B" {
        description
          "TNRDSFUIU07B.";
      }
      enum "ME0DSFUIU07B" {
        description
          "ME0DSFUIU07B.";
      }
      enum "ME0DSFUIK07A" {
        description
          "ME0DSFUIK07A.";
      }
      enum "ME0D0MPUB470" {
        description
          "ME0D0MPUB470.";
      }
      enum "ME0DSFUIE07D" {
        description
          "ME0DSFUIE07D.";
      }
      enum "ME0D0SRUA570" {
        description
          "ME0D0SRUA570.";
      }
      enum "ME0DSFUIE07C" {
        description
          "ME0DSFUIE07C.";
      }
      enum "CR5DVSUF8010" {
        description
          "CR5DVSUF8010.";
      }
      enum "ME0DVSUF8070" {
        description
          "ME0DVSUF8070.";
      }
      enum "CR5DVSUFD010" {
        description
          "CR5DVSUFD010.";
      }
      enum "ME0DVSUFD070" {
        description
          "ME0DVSUFD070.";
      }
      enum "CX6B0BKP0371" {
        description
          "CX6B0BKP0371.";
      }
      enum "CX6B0BKP0372" {
        description
          "CX6B0BKP0372.";
      }
      enum "CR5B0BKP0371" {
        description
          "CR5B0BKP0371.";
      }
      enum "CR5B0BKP0372" {
        description
          "CR5B0BKP0372.";
      }
      enum "CR2B0BKP0210" {
        description
          "CR2B0BKP0210.";
      }
      enum "CR2B0BKP0211" {
        description
          "CR2B0BKP0211.";
      }
      enum "TNRB0BKP0371" {
        description
          "TNRB0BKP0371.";
      }
      enum "TNRB0BKP0372" {
        description
          "TNRB0BKP0372.";
      }
      enum "CR5DVSUID010" {
        description
          "CR5DVSUID010.";
      }
      enum "ME0DVSUID070" {
        description
          "ME0DVSUID070.";
      }
      enum "ME0DVSUF8072" {
        description
          "ME0DVSUF8072.";
      }
      enum "ME0DVSUF8073" {
        description
          "ME0DVSUF8073.";
      }
      enum "CR5DVSUF8011" {
        description
          "CR5DVSUF8011.";
      }
      enum "CR5D0EMGFA7P" {
        description
          "CR5D0EMGFA7P.";
      }
      enum "CR5D00LBXF7P" {
        description
          "CR5D00LBXF7P.";
      }
      enum "CR5DL6XEFG7P" {
        description
          "CR5DL6XEFG7P.";
      }
      enum "CR5D00LFXF7P" {
        description
          "CR5D00LFXF7P.";
      }
      enum "CR5D00E8NC7P" {
        description
          "CR5D00E8NC7P.";
      }
      enum "CX6D0L5XFA1B" {
        description
          "CX6D0L5XFA1B.";
      }
      enum "CX6D0EMGFA1B" {
        description
          "CX6D0EMGFA1B.";
      }
      enum "CX6DISUFA110" {
        description
          "CX6DISUFA110.";
      }
      enum "CX6DISUFA210" {
        description
          "CX6DISUFA210.";
      }
      enum "CX6DISUFB010" {
        description
          "CX6DISUFB010.";
      }
      enum "CX6D0LAXFA10" {
        description
          "CX6D0LAXFA10.";
      }
      enum "CX6D0LBXFA11" {
        description
          "CX6D0LBXFA11.";
      }
      enum "CR5DLAXFAJ7E" {
        description
          "CR5DLAXFAJ7E.";
      }
      enum "CR5DL2XEFG7E" {
        description
          "CR5DL2XEFG7E.";
      }
      enum "CX6DISUFE012" {
        description
          "CX6DISUFE012.";
      }
      enum "CX6DISUFE011" {
        description
          "CX6DISUFE011.";
      }
      enum "CX6DISUFF010" {
        description
          "CX6DISUFF010.";
      }
      enum "CX6D0LFXFA10" {
        description
          "CX6D0LFXFA10.";
      }
      enum "CX6DISUF5110" {
        description
          "CX6DISUF5110.";
      }
      enum "CX6DISUF511B" {
        description
          "CX6DISUF511B.";
      }
      enum "CX6DSFUIE07C" {
        description
          "CX6DSFUIE07C.";
      }
      enum "CX6DSFUIA07D" {
        description
          "CX6DSFUIA07D.";
      }
      enum "CX6D0SRUA511" {
        description
          "CX6D0SRUA511.";
      }
      enum "CX6D0SRUA770" {
        description
          "CX6D0SRUA770.";
      }
      enum "CX6D0LEXFA10" {
        description
          "CX6D0LEXFA10.";
      }
      enum "CX6DSFUIE07B" {
        description
          "CX6DSFUIE07B.";
      }
      enum "CR5D0SRUA770" {
        description
          "CR5D0SRUA770.";
      }
      enum "CX6D0MPUB411" {
        description
          "CX6D0MPUB411.";
      }
      enum "CR5D0SRUB570" {
        description
          "CR5D0SRUB570.";
      }
      enum "CR5D0SRUB571" {
        description
          "CR5D0SRUB571.";
      }
      enum "CX6D0SRUB510" {
        description
          "CX6D0SRUB510.";
      }
      enum "ME0D0SRUB570" {
        description
          "ME0D0SRUB570.";
      }
      enum "TNRD0SRUB570" {
        description
          "TNRD0SRUB570.";
      }
      enum "CX6DISUFM010" {
        description
          "CX6DISUFM010.";
      }
      enum "CR5DSFUIA07D" {
        description
          "CR5DSFUIA07D.";
      }
      enum "CR5DLPUFM07B" {
        description
          "CR5DLPUFM07B.";
      }
      enum "CR5D00LMXF7B" {
        description
          "CR5D00LMXF7B.";
      }
      enum "CR5DE2NLFX7B" {
        description
          "CR5DE2NLFX7B.";
      }
      enum "CR5D00E4NC7B" {
        description
          "CR5D00E4NC7B.";
      }
      enum "CX6D0LEXFA11" {
        description
          "CX6D0LEXFA11.";
      }
      enum "CR5D00E8NC7C" {
        description
          "CR5D00E8NC7C.";
      }
      enum "CR5D00LMXF7C" {
        description
          "CR5D00LMXF7C.";
      }
      enum "CR5DE2NLFX7C" {
        description
          "CR5DE2NLFX7C.";
      }
      enum "CR5D00E4NC7C" {
        description
          "CR5D00E4NC7C.";
      }
      enum "ME0DL2XEFG7E" {
        description
          "ME0DL2XEFG7E.";
      }
      enum "CR5D0L5XFA7E" {
        description
          "CR5D0L5XFA7E.";
      }
      enum "CR5D0L5XFA7F" {
        description
          "CR5D0L5XFA7F.";
      }
      enum "CR5DLAXFAJ7F" {
        description
          "CR5DLAXFAJ7F.";
      }
      enum "ME0D0L5XXE71" {
        description
          "ME0D0L5XXE71.";
      }
      enum "ME0D0LAXXH71" {
        description
          "ME0D0LAXXH71.";
      }
      enum "CR5DL2XFFG7E" {
        description
          "CR5DL2XFFG7E.";
      }
      enum "ME0DL2XEFG8E" {
        description
          "ME0DL2XEFG8E.";
      }
      enum "CX6DSFUIM01B" {
        description
          "CX6DSFUIM01B.";
      }
      enum "CX6DSFUIM01C" {
        description
          "CX6DSFUIM01C.";
      }
      enum "CX6D0MPUB510" {
        description
          "CX6D0MPUB510.";
      }
      enum "CX6D0SRUA810" {
        description
          "CX6D0SRUA810.";
      }
      enum "CX6D0MPUD410" {
        description
          "CX6D0MPUD410.";
      }
      enum "ME0DSFUIM07B" {
        description
          "ME0DSFUIM07B.";
      }
      enum "ME0DSFUIM07C" {
        description
          "ME0DSFUIM07C.";
      }
      enum "ME0D0SRUA770" {
        description
          "ME0D0SRUA770.";
      }
      enum "ME0DSFUIA07D" {
        description
          "ME0DSFUIA07D.";
      }
      enum "ME0D00MPUK70" {
        description
          "ME0D00MPUK70.";
      }
      enum "ME0DBSU24071" {
        description
          "ME0DBSU24071.";
      }
      enum "CR57SRU200B" {
        description
          "CR57SRU200B.";
      }
      enum "CR5D0MPUB571" {
        description
          "CR5D0MPUB571.";
      }
      enum "CX6D0MPUB571" {
        description
          "CX6D0MPUB571.";
      }
      enum "TNRD0MPUB571" {
        description
          "TNRD0MPUB571.";
      }
      enum "ME0D0MPUB571" {
        description
          "ME0D0MPUB571.";
      }
      enum "CR5DMPUX8670" {
        description
          "CR5DMPUX8670.";
      }
      enum "CX6DMPUX8670" {
        description
          "CX6DMPUX8670.";
      }
      enum "ME0DMPUX8670" {
        description
          "ME0DMPUX8670.";
      }
      enum "CR5D0MPUD471" {
        description
          "CR5D0MPUD471.";
      }
      enum "CX6D0MPUD471" {
        description
          "CX6D0MPUD471.";
      }
      enum "TNRD0MPUD471" {
        description
          "TNRD0MPUD471.";
      }
      enum "CR5D0SRUA871" {
        description
          "CR5D0SRUA871.";
      }
      enum "CX6D0SRUA871" {
        description
          "CX6D0SRUA871.";
      }
      enum "TNRD0SRUA871" {
        description
          "TNRD0SRUA871.";
      }
      enum "ME0D0SRUA871" {
        description
          "ME0D0SRUA871.";
      }
      enum "CR5D0SRUA971" {
        description
          "CR5D0SRUA971.";
      }
      enum "CX6D0SRUA971" {
        description
          "CX6D0SRUA971.";
      }
      enum "TNRD0SRUA971" {
        description
          "TNRD0SRUA971.";
      }
      enum "ME0D0SRUA971" {
        description
          "ME0D0SRUA971.";
      }
      enum "CR5D00E8NB60" {
        description
          "CR5D00E8NB60.";
      }
      enum "ME0D0L8NCA70" {
        description
          "ME0D0L8NCA70.";
      }
      enum "ME0D0L4NCB70" {
        description
          "ME0D0L4NCB70.";
      }
      enum "ME0D0L2NCB70" {
        description
          "ME0D0L2NCB70.";
      }
      enum "ME0D0LFXFA70" {
        description
          "ME0D0LFXFA70.";
      }
      enum "ME0D0LMXFA70" {
        description
          "ME0D0LMXFA70.";
      }
      enum "ME0D0E4NCM70" {
        description
          "ME0D0E4NCM70.";
      }
      enum "ME0D0LKXFB70" {
        description
          "ME0D0LKXFB70.";
      }
      enum "ME0DE2NLEX7B" {
        description
          "ME0DE2NLEX7B.";
      }
      enum "ME0DL3XEFG7B" {
        description
          "ME0DL3XEFG7B.";
      }
      enum "ME0D0LEXFB71" {
        description
          "ME0D0LEXFB71.";
      }
      enum "ME0D0LAXFA70" {
        description
          "ME0D0LAXFA70.";
      }
      enum "ME0D0LEXFB70" {
        description
          "ME0D0LEXFB70.";
      }
      enum "ME0D0E2NCB70" {
        description
          "ME0D0E2NCB70.";
      }
      enum "ME0D0EMGFB70" {
        description
          "ME0D0EMGFB70.";
      }
      enum "ME0D0LAXXB70" {
        description
          "ME0D0LAXXB70.";
      }
      enum "ME0D0L5XXB70" {
        description
          "ME0D0L5XXB70.";
      }
      enum "CR5DLPUFE07E" {
        description
          "CR5DLPUFE07E.";
      }
      enum "ME0DBSUFA071" {
        description
          "ME0DBSUFA071.";
      }
      enum "ME0DBSUFF071" {
        description
          "ME0DBSUFF071.";
      }
      enum "ME0DBSUFK070" {
        description
          "ME0DBSUFK070.";
      }
      enum "CR5DLPUFK070" {
        description
          "CR5DLPUFK070.";
      }
      enum "CR9DLPUFK080" {
        description
          "CR9DLPUFK080.";
      }
      enum "CR9D00EDNB8P" {
        description
          "CR9D00EDNB8P.";
      }
      enum "CR9D00E8NC8P" {
        description
          "CR9D00E8NC8P.";
      }
      enum "CR9D00D8NC8P" {
        description
          "CR9D00D8NC8P.";
      }
      enum "CR9D00EPXF8P" {
        description
          "CR9D00EPXF8P.";
      }
      enum "CR5D00LKXF6P" {
        description
          "CR5D00LKXF6P.";
      }
      enum "CR5D00EDNB6P" {
        description
          "CR5D00EDNB6P.";
      }
    }
    description
      "";
  }
  typedef devmSubCardType {
    type enumeration {
      enum "unknown" {
        description
          "Unknown card.";
      }
      enum "CR2D00EEGF10" {
        description
          "CR2D00EEGF10.";
      }
      enum "CR5D00EEGF70" {
        description
          "CR5D00EEGF70.";
      }
      enum "CR57E8NCB0" {
        description
          "CR57E8NCB0.";
      }
      enum "ME0D00E8GE71" {
        description
          "ME0D00E8GE71.";
      }
      enum "ME0D00EAGF70" {
        description
          "ME0D00EAGF70.";
      }
      enum "ME0D00L4XF72" {
        description
          "ME0D00L4XF72.";
      }
      enum "ME0DL1XE8G71" {
        description
          "ME0DL1XE8G71.";
      }
      enum "ME0D00L2XF71" {
        description
          "ME0D00L2XF71.";
      }
      enum "ME0D00L4XF70" {
        description
          "ME0D00L4XF70.";
      }
      enum "ME0DL1XE8G70" {
        description
          "ME0DL1XE8G70.";
      }
      enum "ME0D00L2XF70" {
        description
          "ME0D00L2XF70.";
      }
      enum "ME0D00E8GF71" {
        description
          "ME0D00E8GF71.";
      }
      enum "ME0D00E8GE70" {
        description
          "ME0D00E8GE70.";
      }
      enum "ME0D00C4CF71" {
        description
          "ME0D00C4CF71.";
      }
      enum "ME0D000IE170" {
        description
          "ME0D000IE170.";
      }
      enum "ME0D000IE171" {
        description
          "ME0D000IE171.";
      }
      enum "ME0D000DE170" {
        description
          "ME0D000DE170.";
      }
      enum "ME0D000DE171" {
        description
          "ME0D000DE171.";
      }
      enum "ME0D00P4CF70" {
        description
          "ME0D00P4CF70.";
      }
      enum "ME0DP2C1HF70" {
        description
          "ME0DP2C1HF70.";
      }
      enum "ME0D00AUXQ10" {
        description
          "ME0D00AUXQ10.";
      }
      enum "ME0D08CWDM70" {
        description
          "ME0D08CWDM70.";
      }
      enum "ME0D00C4T370" {
        description
          "ME0D00C4T370.";
      }
      enum "ME0D0EAGFH70" {
        description
          "ME0D0EAGFH70.";
      }
      enum "ME0D0L2XFH71" {
        description
          "ME0D0L2XFH71.";
      }
      enum "ME2D00E8GE12" {
        description
          "ME2D00E8GE12.";
      }
      enum "ME2D00EAGF10" {
        description
          "ME2D00EAGF10.";
      }
      enum "ME2D00L4XF11" {
        description
          "ME2D00L4XF11.";
      }
      enum "ME2DL1XE8G11" {
        description
          "ME2DL1XE8G11.";
      }
      enum "ME2D00L2XF12" {
        description
          "ME2D00L2XF12.";
      }
      enum "CR5D00P2XX72" {
        description
          "CR5D00P2XX72.";
      }
      enum "CR57L4XEBG0" {
        description
          "CR57L4XEBG0.";
      }
      enum "CR57TBXF00" {
        description
          "CR57TBXF00.";
      }
      enum "CR57T6XF00" {
        description
          "CR57T6XF00.";
      }
      enum "CR5D00T1MC60" {
        description
          "CR5D00T1MC60.";
      }
      enum "CR5D00TBXF70" {
        description
          "CR5D00TBXF70.";
      }
      enum "CR5D00T6XF70" {
        description
          "CR5D00T6XF70.";
      }
      enum "CR53CFE10" {
        description
          "CR53CFE10.";
      }
      enum "CR5D00C2CF70" {
        description
          "CR5D00C2CF70.";
      }
      enum "CR5D00C4CF70" {
        description
          "CR5D00C4CF70.";
      }
      enum "CR5D00C8CF71" {
        description
          "CR5D00C8CF71.";
      }
      enum "CX6D00C8CF10" {
        description
          "CX6D00C8CF10.";
      }
      enum "CX6D0L2XFA10" {
        description
          "CX6D0L2XFA10.";
      }
      enum "CR57L3XFB0" {
        description
          "CR57L3XFB0.";
      }
      enum "CR57L2XFB2" {
        description
          "CR57L2XFB2.";
      }
      enum "CR57L4XFB2" {
        description
          "CR57L4XFB2.";
      }
      enum "CR57L5XFB2" {
        description
          "CR57L5XFB2.";
      }
      enum "CR57EMGFC0" {
        description
          "CR57EMGFC0.";
      }
      enum "CR57EFGFC0" {
        description
          "CR57EFGFC0.";
      }
      enum "CR57L1XEDG0" {
        description
          "CR57L1XEDG0.";
      }
      enum "ME0D0LBXXB7H" {
        description
          "ME0D0LBXXB7H.";
      }
      enum "ME0D2L1NXB7H" {
        description
          "ME0D2L1NXB7H.";
      }
      enum "ME0D0L1NXB7H" {
        description
          "ME0D0L1NXB7H.";
      }
      enum "CX6D0E2NCA10" {
        description
          "CX6D0E2NCA10.";
      }
      enum "CX6D0LFXFA11" {
        description
          "CX6D0LFXFA11.";
      }
      enum "ME0D0LAXFE7H" {
        description
          "ME0D0LAXFE7H.";
      }
      enum "ME0D0LAXFB7H" {
        description
          "ME0D0LAXFB7H.";
      }
      enum "ME0D0LAXFH7H" {
        description
          "ME0D0LAXFH7H.";
      }
      enum "CR57LAXFB1" {
        description
          "CR57LAXFB1.";
      }
      enum "CR57L2XEIG0" {
        description
          "CR57L2XEIG0.";
      }
      enum "CR57L5XFC0" {
        description
          "CR57L5XFC0.";
      }
      enum "ME0D0L5XXE7H" {
        description
          "ME0D0L5XXE7H.";
      }
      enum "ME0D0L6XXB7H" {
        description
          "ME0D0L6XXB7H.";
      }
      enum "ME0D0L2XXE7H" {
        description
          "ME0D0L2XXE7H.";
      }
      enum "ME0D0L5XXE7F" {
        description
          "ME0D0L5XXE7F.";
      }
      enum "ME0D0EFGFE7H" {
        description
          "ME0D0EFGFE7H.";
      }
      enum "ME0D0L2XXB7H" {
        description
          "ME0D0L2XXB7H.";
      }
      enum "ME0D0L5XXB7F" {
        description
          "ME0D0L5XXB7F.";
      }
      enum "ME0D0L5XXB7H" {
        description
          "ME0D0L5XXB7H.";
      }
      enum "ME0D0EFGFB7H" {
        description
          "ME0D0EFGFB7H.";
      }
      enum "CR57D2NT00" {
        description
          "CR57D2NT00.";
      }
      enum "CR53P8CF0" {
        description
          "CR53P8CF0.";
      }
      enum "CR53P4CF0" {
        description
          "CR53P4CF0.";
      }
      enum "CR5D00P2CF70" {
        description
          "CR5D00P2CF70.";
      }
      enum "CR2D00T4XF70" {
        description
          "CR2D00T4XF70.";
      }
      enum "CR2D00E1MF70" {
        description
          "CR2D00E1MF70.";
      }
      enum "CR5D00E1MF70" {
        description
          "CR5D00E1MF70.";
      }
      enum "CR5D00T4XF70" {
        description
          "CR5D00T4XF70.";
      }
      enum "CR5D0L5XFA7L" {
        description
          "CR5D0L5XFA7L.";
      }
      enum "CR5DL2XEIG7L" {
        description
          "CR5DL2XEIG7L.";
      }
      enum "CR5D0EMGFA7L" {
        description
          "CR5D0EMGFA7L.";
      }
      enum "CR5D0L5XFA72" {
        description
          "CR5D0L5XFA72.";
      }
      enum "CR5D0LAXFE70" {
        description
          "CR5D0LAXFE70.";
      }
      enum "CR5D00LAXF70" {
        description
          "CR5D00LAXF70.";
      }
      enum "CR5D0L5XFA70" {
        description
          "CR5D0L5XFA70.";
      }
      enum "CR5M0E8GFA30" {
        description
          "CR5M0E8GFA30.";
      }
      enum "CR5D0L2XFA70" {
        description
          "CR5D0L2XFA70.";
      }
      enum "CR5D0EEGEA70" {
        description
          "CR5D0EEGEA70.";
      }
      enum "CR5D00L2XEFGFA71" {
        description
          "CR5D00L2XEFGFA71.";
      }
      enum "CR5D00L4XEKGFB71" {
        description
          "CR5D00L4XEKGFB71.";
      }
      enum "CR5D00AUXQ10" {
        description
          "CR5D00AUXQ10.";
      }
      enum "CR2D0L2XFH10" {
        description
          "CR2D0L2XFH10.";
      }
      enum "CR5D0L2XFH71" {
        description
          "CR5D0L2XFH71.";
      }
      enum "CR2D00L2XF12" {
        description
          "CR2D00L2XF12.";
      }
      enum "CX6D00L2XF11" {
        description
          "CX6D00L2XF11.";
      }
      enum "CR5D08CWDM70" {
        description
          "CR5D08CWDM70.";
      }
      enum "CR5D00L2XF71" {
        description
          "CR5D00L2XF71.";
      }
      enum "CR2D00E8GE12" {
        description
          "CR2D00E8GE12.";
      }
      enum "CX6D00E8GE11" {
        description
          "CX6D00E8GE11.";
      }
      enum "CR5D00E8GE71" {
        description
          "CR5D00E8GE71.";
      }
      enum "CR2DL1XE8G11" {
        description
          "CR2DL1XE8G11.";
      }
      enum "CX6DL1XE8G11" {
        description
          "CX6DL1XE8G11.";
      }
      enum "CR5DL1XE8G71" {
        description
          "CR5DL1XE8G71.";
      }
      enum "CR2D00L4XF11" {
        description
          "CR2D00L4XF11.";
      }
      enum "CX6D00L4XF11" {
        description
          "CX6D00L4XF11.";
      }
      enum "CR5D00L4XF72" {
        description
          "CR5D00L4XF72.";
      }
      enum "CR2D00EAGF10" {
        description
          "CR2D00EAGF10.";
      }
      enum "CX6D00EAGF10" {
        description
          "CX6D00EAGF10.";
      }
      enum "CR5D00EAGF70" {
        description
          "CR5D00EAGF70.";
      }
      enum "CR2D0EAGFH10" {
        description
          "CR2D0EAGFH10.";
      }
      enum "CR5D0EAGFH70" {
        description
          "CR5D0EAGFH70.";
      }
      enum "CR52P2XX" {
        description
          "CR52P2XX.";
      }
      enum "CR57E8NC" {
        description
          "CR57E8NC.";
      }
      enum "CR52P4XX" {
        description
          "CR52P4XX.";
      }
      enum "CR52P8UF" {
        description
          "CR52P8UF.";
      }
      enum "CR52EEGF" {
        description
          "CR52EEGF.";
      }
      enum "CR52E1XX" {
        description
          "CR52E1XX.";
      }
      enum "CR52E4XX" {
        description
          "CR52E4XX.";
      }
      enum "CR52W4XX" {
        description
          "CR52W4XX.";
      }
      enum "CR52EAGF" {
        description
          "CR52EAGF.";
      }
      enum "CR52P4UF" {
        description
          "CR52P4UF.";
      }
      enum "CR52E2XX" {
        description
          "CR52E2XX.";
      }
      enum "CR52W2XX" {
        description
          "CR52W2XX.";
      }
      enum "CR52P1XX" {
        description
          "CR52P1XX.";
      }
      enum "CR52W1XX" {
        description
          "CR52W1XX.";
      }
      enum "CR56L5XX" {
        description
          "CR56L5XX.";
      }
      enum "CR56E1NC" {
        description
          "CR56E1NC.";
      }
      enum "CR56P2XX" {
        description
          "CR56P2XX.";
      }
      enum "CR56L2XX" {
        description
          "CR56L2XX.";
      }
      enum "CR56E2XX" {
        description
          "CR56E2XX.";
      }
      enum "CR56D2XX" {
        description
          "CR56D2XX.";
      }
      enum "CR56E5XX" {
        description
          "CR56E5XX.";
      }
      enum "CR56P1MZ" {
        description
          "CR56P1MZ.";
      }
      enum "CR56EFGF" {
        description
          "CR56EFGF.";
      }
      enum "CR52P8CF" {
        description
          "CR52P8CF.";
      }
      enum "CR2D00C1CF11" {
        description
          "CR2D00C1CF11.";
      }
      enum "CR52P2UF" {
        description
          "CR52P2UF.";
      }
      enum "CR52P1UF" {
        description
          "CR52P1UF.";
      }
      enum "CR55OFC100B" {
        description
          "CR55OFC100B.";
      }
      enum "CR55OFC400D" {
        description
          "CR55OFC400D.";
      }
      enum "CR5D0OFCK051" {
        description
          "CR5D0OFCK051.";
      }
      enum "CR55OFC400A" {
        description
          "CR55OFC400A.";
      }
      enum "CR5M0OFCK050" {
        description
          "CR5M0OFCK050.";
      }
      enum "CR55OFC1TA" {
        description
          "CR55OFC1TA.";
      }
      enum "CR5D0OFCT050" {
        description
          "CR5D0OFCT050.";
      }
      enum "CR55OFC400B" {
        description
          "CR55OFC400B.";
      }
      enum "CR55OFC1TB" {
        description
          "CR55OFC1TB.";
      }
      enum "CR50OFC1TC" {
        description
          "CR50OFC1TC.";
      }
      enum "CR50OFC1TD" {
        description
          "CR50OFC1TD.";
      }
      enum "CR52OFCB" {
        description
          "CR52OFCB.";
      }
      enum "CR55OFC100A" {
        description
          "CR55OFC100A.";
      }
      enum "CR55OFC40" {
        description
          "CR55OFC40.";
      }
      enum "CR55OFCA" {
        description
          "CR55OFCA.";
      }
      enum "CR55C-OFCA" {
        description
          "CR55C-OFCA.";
      }
      enum "CR52OFCV" {
        description
          "CR52OFCV.";
      }
      enum "CFCARD" {
        description
          "CF card.";
      }
      enum "CR53P1MZ" {
        description
          "CR53P1MZ.";
      }
      enum "CR52P4HF" {
        description
          "CR52P4HF.";
      }
      enum "CR52EMGE" {
        description
          "CR52EMGE.";
      }
      enum "CR52EFGE" {
        description
          "CR52EFGE.";
      }
      enum "CR52E5GF" {
        description
          "CR52E5GF.";
      }
      enum "CR52P4CF" {
        description
          "CR52P4CF.";
      }
      enum "CR52D1MV" {
        description
          "CR52D1MV.";
      }
      enum "CR52EKGFY" {
        description
          "CR52EKGFY.";
      }
      enum "CR57EFGF" {
        description
          "CR57EFGF.";
      }
      enum "CR56E1NCC" {
        description
          "CR56E1NCC.";
      }
      enum "CR52P1XZ" {
        description
          "CR52P1XZ.";
      }
      enum "CR52E1XZ" {
        description
          "CR52E1XZ.";
      }
      enum "CR52W1XZ" {
        description
          "CR52W1XZ.";
      }
      enum "SPU" {
        description
          "SPU.";
      }
      enum "TSUA" {
        description
          "TSUA.";
      }
      enum "CR56E1MC" {
        description
          "CR56E1MC.";
      }
      enum "CR56LAXFA" {
        description
          "CR56LAXFA.";
      }
      enum "CR56E2ND" {
        description
          "CR56E2ND.";
      }
      enum "CR56E6MB" {
        description
          "CR56E6MB.";
      }
      enum "CR56LEXF" {
        description
          "CR56LEXF.";
      }
      enum "CR56E1NCB" {
        description
          "CR56E1NCB.";
      }
      enum "CR56L5XFB" {
        description
          "CR56L5XFB.";
      }
      enum "CR56E5XFB" {
        description
          "CR56E5XFB.";
      }
      enum "CR56P8UF" {
        description
          "CR56P8UF.";
      }
      enum "CR56LFXF" {
        description
          "CR56LFXF.";
      }
      enum "CR56E2NCC" {
        description
          "CR56E2NCC.";
      }
      enum "CR56E5MB" {
        description
          "CR56E5MB.";
      }
      enum "CR5D00L5XX60" {
        description
          "CR5D00L5XX60.";
      }
      enum "CR5D00E5XX60" {
        description
          "CR5D00E5XX60.";
      }
      enum "CR5D00L2XX60" {
        description
          "CR5D00L2XX60.";
      }
      enum "CR5D00E2XX60" {
        description
          "CR5D00E2XX60.";
      }
      enum "CR5D00EFGF60" {
        description
          "CR5D00EFGF60.";
      }
      enum "CR5D00P1MZ60" {
        description
          "CR5D00P1MZ60.";
      }
      enum "CR5D00P2XX60" {
        description
          "CR5D00P2XX60.";
      }
      enum "CR5M00E1MC60" {
        description
          "CR5M00E1MC60.";
      }
      enum "CR5D00E1NC60" {
        description
          "CR5D00E1NC60.";
      }
      enum "CR5D00LAXX60" {
        description
          "CR5D00LAXX60.";
      }
      enum "CR5D00E2NC61" {
        description
          "CR5D00E2NC61.";
      }
      enum "CR5D00E6MF61" {
        description
          "CR5D00E6MF61.";
      }
      enum "CR5D00LEXF61" {
        description
          "CR5D00LEXF61.";
      }
      enum "CR5D00E1NC61" {
        description
          "CR5D00E1NC61.";
      }
      enum "CR5D00LMXF61" {
        description
          "CR5D00LMXF61.";
      }
      enum "CR5D00LAXF60" {
        description
          "CR5D00LAXF60.";
      }
      enum "CR5D00L5XF60" {
        description
          "CR5D00L5XF60.";
      }
      enum "CR5D00E5XF60" {
        description
          "CR5D00E5XF60.";
      }
      enum "CR5D00P8UF60" {
        description
          "CR5D00P8UF60.";
      }
      enum "CR5D00E2NC62" {
        description
          "CR5D00E2NC62.";
      }
      enum "CR5D00E5MF61" {
        description
          "CR5D00E5MF61.";
      }
      enum "CR5D0OFCA060" {
        description
          "CR5D0OFCA060.";
      }
      enum "CX6D00E8GE10" {
        description
          "CX6D00E8GE10.";
      }
      enum "CR5D00E8GE70" {
        description
          "CR5D00E8GE70.";
      }
      enum "CR2D00E8GE11" {
        description
          "CR2D00E8GE11.";
      }
      enum "CX6D00L2XF10" {
        description
          "CX6D00L2XF10.";
      }
      enum "CR5D00L2XF70" {
        description
          "CR5D00L2XF70.";
      }
      enum "CR2D00L2XF11" {
        description
          "CR2D00L2XF11.";
      }
      enum "CX6D00E8GF10" {
        description
          "CX6D00E8GF10.";
      }
      enum "CR5D00E8GF71" {
        description
          "CR5D00E8GF71.";
      }
      enum "CR2D00E8GF11" {
        description
          "CR2D00E8GF11.";
      }
      enum "CX6D000IE170" {
        description
          "CX6D000IE170.";
      }
      enum "CX6D000IE171" {
        description
          "CX6D000IE171.";
      }
      enum "CR5D00P4CF70" {
        description
          "CR5D00P4CF70.";
      }
      enum "CR2D00P4CF11" {
        description
          "CR2D00P4CF11.";
      }
      enum "CX6D00L4XF10" {
        description
          "CX6D00L4XF10.";
      }
      enum "CR5D00L4XF70" {
        description
          "CR5D00L4XF70.";
      }
      enum "CR2D00L4XF10" {
        description
          "CR2D00L4XF10.";
      }
      enum "CX6DL1XE8G10" {
        description
          "CX6DL1XE8G10.";
      }
      enum "CR5DL1XE8G70" {
        description
          "CR5DL1XE8G70.";
      }
      enum "CR2DL1XE8G10" {
        description
          "CR2DL1XE8G10.";
      }
      enum "CR5D00C4CF71" {
        description
          "CR5D00C4CF71.";
      }
      enum "CX6D00C4CF11" {
        description
          "CX6D00C4CF11.";
      }
      enum "CR2D00C4CF11" {
        description
          "CR2D00C4CF11.";
      }
      enum "CR5D000IE170" {
        description
          "CR5D000IE170.";
      }
      enum "CX6D000IE110" {
        description
          "CX6D000IE110.";
      }
      enum "CR2D000IE110" {
        description
          "CR2D000IE110.";
      }
      enum "CR5D000IE171" {
        description
          "CR5D000IE171.";
      }
      enum "CX6D000IE111" {
        description
          "CX6D000IE111.";
      }
      enum "CR2D000IE111" {
        description
          "CR2D000IE111.";
      }
      enum "CR5D000DE170" {
        description
          "CR5D000DE170.";
      }
      enum "CX6D000DE110" {
        description
          "CX6D000DE110.";
      }
      enum "CR2D000DE110" {
        description
          "CR2D000DE110.";
      }
      enum "CR5D000DE171" {
        description
          "CR5D000DE171.";
      }
      enum "CX6D000DE111" {
        description
          "CX6D000DE111.";
      }
      enum "CR2D000DE111" {
        description
          "CR2D000DE111.";
      }
      enum "CR5D00C4T370" {
        description
          "CR5D00C4T370.";
      }
      enum "CR57EFGFB" {
        description
          "CR57EFGFB.";
      }
      enum "CR57EFGFB2" {
        description
          "CR57EFGFB2.";
      }
      enum "CR57LBXF" {
        description
          "CR57LBXF.";
      }
      enum "CR57LBXF2" {
        description
          "CR57LBXF2.";
      }
      enum "CR57E1NCB2" {
        description
          "CR57E1NCB2.";
      }
      enum "CR57L6XF" {
        description
          "CR57L6XF.";
      }
      enum "CR57L6XF0" {
        description
          "CR57L6XF0.";
      }
      enum "CR57L6XFB" {
        description
          "CR57L6XFB.";
      }
      enum "CR57P8UF" {
        description
          "CR57P8UF.";
      }
      enum "CR5D0P8UF70" {
        description
          "CR5D0P8UF70.";
      }
      enum "CR57E1MCB" {
        description
          "CR57E1MCB.";
      }
      enum "CR57E1MCB2" {
        description
          "CR57E1MCB2.";
      }
      enum "CX68MD8A" {
        description
          "CX68MD8A.";
      }
      enum "CR56E8NC" {
        description
          "CR56E8NC.";
      }
      enum "CR56EFMB" {
        description
          "CR56EFMB.";
      }
      enum "CR50OFC400C" {
        description
          "CR50OFC400C.";
      }
      enum "CR5D00LFXF74" {
        description
          "CR5D00LFXF74.";
      }
      enum "CR5D00E2NC72" {
        description
          "CR5D00E2NC72.";
      }
      enum "CR57LFXFE1" {
        description
          "CR57LFXFE1.";
      }
      enum "CR57E2NCE1" {
        description
          "CR57E2NCE1.";
      }
      enum "CR57LFXFE" {
        description
          "CR57LFXFE.";
      }
      enum "CR57E2NCE" {
        description
          "CR57E2NCE.";
      }
      enum "CR5D00LBXF72" {
        description
          "CR5D00LBXF72.";
      }
      enum "CR5D0L6XFA70" {
        description
          "CR5D0L6XFA70.";
      }
      enum "CR5D00E1NC75" {
        description
          "CR5D00E1NC75.";
      }
      enum "CR5D0EFGFA71" {
        description
          "CR5D0EFGFA71.";
      }
      enum "CR5D00E1MC70" {
        description
          "CR5D00E1MC70.";
      }
      enum "CR5D00P8UF70" {
        description
          "CR5D00P8UF70.";
      }
      enum "CR5D00E1NC74" {
        description
          "CR5D00E1NC74.";
      }
      enum "CR5D00LBXF71" {
        description
          "CR5D00LBXF71.";
      }
      enum "CR57L2XFB" {
        description
          "CR57L2XFB.";
      }
      enum "CR5D0L2XFA71" {
        description
          "CR5D0L2XFA71.";
      }
      enum "CR5D0EFGFA70" {
        description
          "CR5D0EFGFA70.";
      }
      enum "CR57L2XFC2" {
        description
          "CR57L2XFC2.";
      }
      enum "CR2DP4C2HF11" {
        description
          "CR2DP4C2HF11.";
      }
      enum "CR5DP4C2HF70" {
        description
          "CR5DP4C2HF70.";
      }
      enum "CR2DP2C1HF11" {
        description
          "CR2DP2C1HF11.";
      }
      enum "CR5DP2C1HF70" {
        description
          "CR5DP2C1HF70.";
      }
      enum "CR5D00N2NC61" {
        description
          "CR5D00N2NC61.";
      }
      enum "CR5D00E1NC62" {
        description
          "CR5D00E1NC62.";
      }
      enum "CR5D00L2NC63" {
        description
          "CR5D00L2NC63.";
      }
      enum "CR5D00LEXF63" {
        description
          "CR5D00LEXF63.";
      }
      enum "CR5D00SP8010" {
        description
          "CR5D00SP8010.";
      }
      enum "CR5D00SPD010" {
        description
          "CR5D00SPD010.";
      }
      enum "ME0D00SP8070" {
        description
          "ME0D00SP8070.";
      }
      enum "ME0D00SPD070" {
        description
          "ME0D00SPD070.";
      }
      enum "CX6D0E8GFA10" {
        description
          "CX6D0E8GFA10.";
      }
      enum "CX6D00CFE110" {
        description
          "CX6D00CFE110.";
      }
      enum "CX6D00C2CF10" {
        description
          "CX6D00C2CF10.";
      }
      enum "CX6D0L5XFA10" {
        description
          "CX6D0L5XFA10.";
      }
      enum "CX6D0L2XFA11" {
        description
          "CX6D0L2XFA11.";
      }
      enum "CX6D0EFGFA10" {
        description
          "CX6D0EFGFA10.";
      }
      enum "CX6D0EEGEA10" {
        description
          "CX6D0EEGEA10.";
      }
      enum "CX6DL1XESG1A" {
        description
          "CX6DL1XESG1A.";
      }
      enum "CX6DL2XEAG1A" {
        description
          "CX6DL2XEAG1A.";
      }
      enum "CX6D0L5XFA12" {
        description
          "CX6D0L5XFA12.";
      }
      enum "CX6D0EFGFA11" {
        description
          "CX6D0EFGFA11.";
      }
      enum "CX6D0E1NCA10" {
        description
          "CX6D0E1NCA10.";
      }
      enum "CX6D0E1MCA10" {
        description
          "CX6D0E1MCA10.";
      }
      enum "CX6D0L5XFH10" {
        description
          "CX6D0L5XFH10.";
      }
      enum "CX6D0L6XFA10" {
        description
          "CX6D0L6XFA10.";
      }
      enum "CX6D0LBXFA10" {
        description
          "CX6D0LBXFA10.";
      }
      enum "CX6D0LAXFA12" {
        description
          "CX6D0LAXFA12.";
      }
      enum "CX6D0E3MFA10" {
        description
          "CX6D0E3MFA10.";
      }
      enum "CX6D0LAXFH10" {
        description
          "CX6D0LAXFH10.";
      }
      enum "CX6D0LBXFA12" {
        description
          "CX6D0LBXFA12.";
      }
      enum "CR5D0EFGFE70" {
        description
          "CR5D0EFGFE70.";
      }
      enum "CR5D0L5XFE70" {
        description
          "CR5D0L5XFE70.";
      }
      enum "CR5D0L2XFE70" {
        description
          "CR5D0L2XFE70.";
      }
      enum "CR5D0L2XFH70" {
        description
          "CR5D0L2XFH70.";
      }
      enum "CR5D0L5XFE71" {
        description
          "CR5D0L5XFE71.";
      }
      enum "CR5D0L5XFH70" {
        description
          "CR5D0L5XFH70.";
      }
      enum "CR5D0E3MFA70" {
        description
          "CR5D0E3MFA70.";
      }
      enum "CR5D0LAXFH70" {
        description
          "CR5D0LAXFH70.";
      }
      enum "CR57EFGFE2" {
        description
          "CR57EFGFE2.";
      }
      enum "CR57L2XFE2" {
        description
          "CR57L2XFE2.";
      }
      enum "CR57L3XFA2" {
        description
          "CR57L3XFA2.";
      }
      enum "CR57LEXFE01" {
        description
          "CR57LEXFE01.";
      }
      enum "CR57L5XFE2" {
        description
          "CR57L5XFE2.";
      }
      enum "CR57E3MB2" {
        description
          "CR57E3MB2.";
      }
      enum "CR53P1XX0" {
        description
          "CR53P1XX0.";
      }
      enum "CR53P2UF0" {
        description
          "CR53P2UF0.";
      }
      enum "CR53P4UF0" {
        description
          "CR53P4UF0.";
      }
      enum "CR53P8HF0" {
        description
          "CR53P8HF0.";
      }
      enum "CR58E8NCD" {
        description
          "CR58E8NCD.";
      }
      enum "CR58EFMBD" {
        description
          "CR58EFMBD.";
      }
      enum "CR58EPXFB" {
        description
          "CR58EPXFB.";
      }
      enum "CR56E8NCB" {
        description
          "CR56E8NCB.";
      }
      enum "CR56EFMBB" {
        description
          "CR56EFMBB.";
      }
      enum "CR5D00A2CF70" {
        description
          "CR5D00A2CF70.";
      }
      enum "CR2D00A2CF10" {
        description
          "CR2D00A2CF10.";
      }
      enum "CR56E8NCE" {
        description
          "CR56E8NCE.";
      }
      enum "CR56E8NLDXA" {
        description
          "CR56E8NLDXA.";
      }
      enum "CR56EDNBV" {
        description
          "CR56EDNBV.";
      }
      enum "CR56EDNLIXV" {
        description
          "CR56EDNLIXV.";
      }
      enum "CR2D0E8GFH10" {
        description
          "CR2D0E8GFH10.";
      }
      enum "CR2D0L2XFH11" {
        description
          "CR2D0L2XFH11.";
      }
      enum "CR5D0L2XFH72" {
        description
          "CR5D0L2XFH72.";
      }
      enum "CR5D0E8GFH70" {
        description
          "CR5D0E8GFH70.";
      }
      enum "ME0D0EAGFE70" {
        description
          "ME0D0EAGFE70.";
      }
      enum "ME0D0L2XFE71" {
        description
          "ME0D0L2XFE71.";
      }
      enum "CR5D0L5XFE74" {
        description
          "CR5D0L5XFE74.";
      }
      enum "CR5D0L2XFE75" {
        description
          "CR5D0L2XFE75.";
      }
      enum "CR5D0L5XFE76" {
        description
          "CR5D0L5XFE76.";
      }
      enum "ME0D0EFGFE7E" {
        description
          "ME0D0EFGFE7E.";
      }
      enum "ME0D0L5XXE7E" {
        description
          "ME0D0L5XXE7E.";
      }
      enum "ME0D0L5XXE8E" {
        description
          "ME0D0L5XXE8E.";
      }
      enum "ME0D0L2XXE7E" {
        description
          "ME0D0L2XXE7E.";
      }
      enum "ME0D0L2XFH7H" {
        description
          "ME0D0L2XFH7H.";
      }
      enum "ME0D0L5XFH7H" {
        description
          "ME0D0L5XFH7H.";
      }
      enum "CR57L5XFI3" {
        description
          "CR57L5XFI3.";
      }
      enum "CR57L2XFI2" {
        description
          "CR57L2XFI2.";
      }
      enum "CR5D00E1NC79" {
        description
          "CR5D00E1NC79.";
      }
      enum "CR5D00LAXF71" {
        description
          "CR5D00LAXF71.";
      }
      enum "CR2D00LAXF10" {
        description
          "CR2D00LAXF10.";
      }
      enum "CR2D00E1NC10" {
        description
          "CR2D00E1NC10.";
      }
      enum "CR5D1DMD1M01" {
        description
          "CR5D1DMD1M01.";
      }
      enum "CR5D1DMD1M02" {
        description
          "CR5D1DMD1M02.";
      }
      enum "CR5D1DMD1M03" {
        description
          "CR5D1DMD1M03.";
      }
      enum "CR5D1DMD1M04" {
        description
          "CR5D1DMD1M04.";
      }
      enum "CR5D1DMD1M05" {
        description
          "CR5D1DMD1M05.";
      }
      enum "CR5D1DMD1M06" {
        description
          "CR5D1DMD1M06.";
      }
      enum "CR5D1DMD1M07" {
        description
          "CR5D1DMD1M07.";
      }
      enum "CR5D1DMD1M08" {
        description
          "CR5D1DMD1M08.";
      }
      enum "CR5D2DMD2M01" {
        description
          "CR5D2DMD2M01.";
      }
      enum "CR5D2DMD2M02" {
        description
          "CR5D2DMD2M02.";
      }
      enum "CR5D2DMD2M03" {
        description
          "CR5D2DMD2M03.";
      }
      enum "CR5D2DMD2M04" {
        description
          "CR5D2DMD2M04.";
      }
      enum "CR5D0E2NCE70" {
        description
          "CR5D0E2NCE70.";
      }
      enum "CR5D0LEXFE70" {
        description
          "CR5D0LEXFE70.";
      }
      enum "ME0M0LEXFB70" {
        description
          "ME0M0LEXFB70.";
      }
      enum "ME0M0E2NCB70" {
        description
          "ME0M0E2NCB70.";
      }
      enum "CR57EFGFH2" {
        description
          "CR57EFGFH2.";
      }
      enum "CR5D0EFGFE71" {
        description
          "CR5D0EFGFE71.";
      }
      enum "CR58E8NBA" {
        description
          "CR58E8NBA.";
      }
      enum "CR58D8NCA" {
        description
          "CR58D8NCA.";
      }
      enum "CX68LGXF0" {
        description
          "CX68LGXF0.";
      }
      enum "CR5DE2NLEX60" {
        description
          "CR5DE2NLEX60.";
      }
      enum "CR5D00LFXF60" {
        description
          "CR5D00LFXF60.";
      }
      enum "CR5D00E4NB60" {
        description
          "CR5D00E4NB60.";
      }
      enum "CR56E4NBA1" {
        description
          "CR56E4NBA1.";
      }
      enum "CR5D00N4NC60" {
        description
          "CR5D00N4NC60.";
      }
      enum "CR5D00LMXB60" {
        description
          "CR5D00LMXB60.";
      }
      enum "CR5D0EFGFH70" {
        description
          "CR5D0EFGFH70.";
      }
      enum "ME0D0EFGFH7H" {
        description
          "ME0D0EFGFH7H.";
      }
      enum "CR5D0L2XFH73" {
        description
          "CR5D0L2XFH73.";
      }
      enum "ME0D0L2XFH8H" {
        description
          "ME0D0L2XFH8H.";
      }
      enum "CR5D0L5XFH72" {
        description
          "CR5D0L5XFH72.";
      }
      enum "ME0D0L5XFH8H" {
        description
          "ME0D0L5XFH8H.";
      }
      enum "CR5D0EAGFE70" {
        description
          "CR5D0EAGFE70.";
      }
      enum "CR5D0L2XFE71" {
        description
          "CR5D0L2XFE71.";
      }
      enum "CR5D00E1NC77" {
        description
          "CR5D00E1NC77.";
      }
      enum "CR5D00E1NC7A" {
        description
          "CR5D00E1NC7A.";
      }
      enum "ME0D0E1NCB70" {
        description
          "ME0D0E1NCB70.";
      }
      enum "ME0D0E1NCB71" {
        description
          "ME0D0E1NCB71.";
      }
      enum "CR57E1NCF2" {
        description
          "CR57E1NCF2.";
      }
      enum "CX6D0E1NCA11" {
        description
          "CX6D0E1NCA11.";
      }
      enum "CR5D00E1ND70" {
        description
          "CR5D00E1ND70.";
      }
      enum "CR5D00E1ND73" {
        description
          "CR5D00E1ND73.";
      }
      enum "ME0D0E1NDB70" {
        description
          "ME0D0E1NDB70.";
      }
      enum "ME0D0E1NDB71" {
        description
          "ME0D0E1NDB71.";
      }
      enum "CX6D0E1NDA10" {
        description
          "CX6D0E1NDA10.";
      }
      enum "CR5D00E2NB60" {
        description
          "CR5D00E2NB60.";
      }
      enum "CR5D00E2NF70" {
        description
          "CR5D00E2NF70.";
      }
      enum "CR5D3DMR4M01" {
        description
          "CR5D3DMR4M01.";
      }
      enum "CR5D3DMR4M02" {
        description
          "CR5D3DMR4M02.";
      }
      enum "CR5D00MD8A70" {
        description
          "CR5D00MD8A70.";
      }
      enum "CR2D0EAGFE10" {
        description
          "CR2D0EAGFE10.";
      }
      enum "CR2D0L2XFE10" {
        description
          "CR2D0L2XFE10.";
      }
      enum "CR5D0E2NCE71" {
        description
          "CR5D0E2NCE71.";
      }
      enum "ME0M0E2NCB71" {
        description
          "ME0M0E2NCB71.";
      }
      enum "CR5D0LEXFE71" {
        description
          "CR5D0LEXFE71.";
      }
      enum "ME0M0LEXFB71" {
        description
          "ME0M0LEXFB71.";
      }
      enum "CR5D0L6XFH70" {
        description
          "CR5D0L6XFH70.";
      }
      enum "ME0D0L6XFH7H" {
        description
          "ME0D0L6XFH7H.";
      }
      enum "CR5D0LBXFH70" {
        description
          "CR5D0LBXFH70.";
      }
      enum "ME0D0LBXFH7H" {
        description
          "ME0D0LBXFH7H.";
      }
      enum "CR5D00N6GF60" {
        description
          "CR5D00N6GF60.";
      }
      enum "CR5D00NBGF60" {
        description
          "CR5D00NBGF60.";
      }
      enum "CR5D00EEGF71" {
        description
          "CR5D00EEGF71.";
      }
      enum "CR2D00EEGF11" {
        description
          "CR2D00EEGF11.";
      }
      enum "CX6D00EEGF10" {
        description
          "CX6D00EEGF10.";
      }
      enum "CR9D00LFXF80" {
        description
          "CR9D00LFXF80.";
      }
      enum "CR9D00NBXF80" {
        description
          "CR9D00NBXF80.";
      }
      enum "CR9D00N6XF80" {
        description
          "CR9D00N6XF80.";
      }
      enum "CR9D00P8UF80" {
        description
          "CR9D00P8UF80.";
      }
      enum "CR9D00P4XX80" {
        description
          "CR9D00P4XX80.";
      }
      enum "CR57EFGFH3" {
        description
          "CR57EFGFH3.";
      }
      enum "CR57L6XFI02" {
        description
          "CR57L6XFI02.";
      }
      enum "CR57LBXFE2" {
        description
          "CR57LBXFE2.";
      }
      enum "CR57E8NCB1" {
        description
          "CR57E8NCB1.";
      }
    }
    description
      "";
  }
  typedef devmLpuServiceType {
    type enumeration {
      enum "lpu" {
        description
          "LPU.";
      }
      enum "rnr" {
        description
          "RNR.";
      }
      enum "tsu" {
        description
          "TSU.";
      }
      enum "ns" {
        description
          "NS.";
      }
      enum "gre" {
        description
          "GRE.";
      }
    }
    description
      "";
  }
  typedef devmInnerlinkType {
    type enumeration {
      enum "other" {
        description
          "Other.";
      }
      enum "controlChannel" {
        description
          "Control Channel.";
      }
      enum "monitorChannel" {
        description
          "Monitor Channel.";
      }
      enum "forwardChannel" {
        description
          "Forward Channel.";
      }
    }
    description
      "information of enum type";
  }
  typedef devmLsRole {
    type enumeration {
      enum "unknown" {
        description
          "Unknown.";
      }
      enum "mmb" {
        description
          "MMB.";
      }
      enum "plmb" {
        description
          "PLMB.";
      }
      enum "acmb" {
        description
          "ACMB.";
      }
      enum "mb" {
        description
          "MB.";
      }
      enum "lc" {
        description
          "LC.";
      }
    }
    description
      "information of enum type devmLsRole";
  }
  typedef devmEthPortTransMode {
    type enumeration {
      enum "lan" {
        description
          "lan";
      }
      enum "wan" {
        description
          "wan";
      }
    }
    description
      "devmEthPortTransMode";
  }
  typedef devmEntityAdminState {
    type enumeration {
      enum "active" {
        description
          "Active state that enabled service supply. ";
      }
      enum "inactive" {
        description
          "Inactive state that disables service supply.";
      }
      enum "notSupported" {
        description
          "Administration state unsupported.";
      }
    }
    description
      "information of enum type devmEntityAdminState";
  }
  typedef devmEntityOperState {
    type enumeration {
      enum "normal" {
        description
          "Normal.";
      }
      enum "fault" {
        description
          "Fault.";
      }
      enum "unknown" {
        description
          "Unknown.";
      }
      enum "offline" {
        description
          "Offline.";
      }
      enum "opticalNotEquipped" {
        description
          "Optical is not equipped.";
      }
      enum "notSupported" {
        description
          "Unsupported.";
      }
    }
    description
      "information of enum type devmEntityOperState";
  }
  typedef devmEntityPresentState {
    type enumeration {
      enum "online" {
        description
          "";
      }
      enum "offline" {
        description
          "";
      }
      enum "unknown" {
        description
          "";
      }
    }
    description
      "information of enum type devmEntityPresentState";
  }
  typedef devmEntityStandbyState {
    type enumeration {
      enum "notSupported" {
        description
          "Unsupported.";
      }
      enum "master" {
        description
          "Master.";
      }
      enum "slave" {
        description
          "Slave.";
      }
      enum "systemMaster" {
        description
          "System master.";
      }
      enum "systemSlave" {
        description
          "System slave.";
      }
    }
    description
      "information of enum type devmEntityStandbyState";
  }
  typedef devmPwrState {
    type enumeration {
      enum "dc" {
        description
          "dc:";
      }
      enum "ac" {
        description
          "ac:";
      }
      enum "unknown" {
        description
          "unknown:";
      }
    }
    description
      "information of enum type devmPwrState";
  }
  typedef devmRunState {
    type enumeration {
      enum "normal" {
        description
          "Normal.";
      }
      enum "abnormal" {
        description
          "Abnormal.";
      }
      enum "unknown" {
        description
          "Unknown.";
      }
    }
    description
      "information of enum type devmRunState";
  }
  typedef devmLockState {
    type enumeration {
      enum "locked" {
        description
          "locked:";
      }
      enum "unlocked" {
        description
          "unlocked:";
      }
    }
    description
      "information of enum type devmRunState";
  }
  typedef devmWorkMode {
    type enumeration {
      enum "auto" {
        description
          "Automatic.";
      }
      enum "manual" {
        description
          "Manual.";
      }
      enum "silent" {
        description
          "silent.";
      }
      enum "full" {
        description
          "full.";
      }
    }
    description
      "information of enum type devmWorkMode";
  }
  typedef devmBool {
    type enumeration {
      enum "YES" {
        description
          "YES.";
      }
      enum "NO" {
        description
          "NO.";
      }
    }
    description
      "information of enum type devmBool";
  }
  typedef devmPowerWorkMode {
    type enumeration {
      enum "DC" {
        description
          "DC.";
      }
      enum "AC" {
        description
          "AC.";
      }
    }
    description
      "information of enum type devmPowerWorkMode";
  }
  typedef devmSsmlevel {
    type enumeration {
      enum "unknown" {
        description
          "Unknown.";
      }
      enum "prc" {
        description
          "PRC level.";
      }
      enum "tnc" {
        description
          "TNC level.";
      }
      enum "lnc" {
        description
          "LNC level.";
      }
      enum "sets" {
        description
          "SETS level.";
      }
      enum "dnu" {
        description
          "DNU level.";
      }
    }
    description
      "information of enum type devmSsmlevel";
  }
  typedef devmControlFlag {
    type enumeration {
      enum "on" {
        description
          "On.";
      }
      enum "off" {
        description
          "Off.";
      }
    }
    description
      "information of enum type devmControlFlag";
  }
  typedef devmCableState {
    type enumeration {
      enum "plug" {
        description
          "Plug.";
      }
      enum "unplug" {
        description
          "Unplug.";
      }
    }
    description
      "information of enum type devmCableState";
  }
  typedef devmChoice {
    type enumeration {
      enum "force" {
        description
          "force:";
      }
      enum "auto" {
        description
          "auto:";
      }
    }
    description
      "information of enum type devmChoice";
  }
  typedef devmAlarmState {
    type enumeration {
      enum "notSupported" {
        description
          "";
      }
      enum "underRepair" {
        description
          "When the value of under repair is set,the resource is currentlybeing repaired.";
      }
      enum "critical" {
        description
          "When the value of critical is set, one or more criticalalarms are active against the resource.";
      }
      enum "major" {
        description
          "When the value of major is set, one or more major alarms are active againstthe resource.";
      }
      enum "minor" {
        description
          "When the value of minor is set, one or moreminor alarms are active against the resource.";
      }
      enum "warning" {
        description
          "When thevalue of warning is set, one or more warning alarms areactive against the resource.";
      }
      enum "alarmOutstanding" {
        description
          "When the value of alarm outstanding is set, one or morealarms is active against the resource. The fault may or maynot be disabling.";
      }
      enum "indeterminate" {
        description
          "When the value ofindeterminate is set, one or more  alarms of indeterminateseverity are active against the resource.";
      }
    }
    description
      "";
  }
  typedef devmPortType {
    type enumeration {
      enum "unknown" {
        description
          "Unknown.";
      }
      enum "Eth" {
        description
          "Ethernet.";
      }
      enum "Pos" {
        description
          "Pos.";
      }
      enum "Cpos" {
        description
          "CPOS port.";
      }
      enum "E1" {
        description
          "E1 port.";
      }
      enum "GE" {
        description
          "GE.";
      }
      enum "10GE" {
        description
          "10GE.";
      }
      enum "GF" {
        description
          "GF.";
      }
      enum "10GF" {
        description
          "10GF.";
      }
      enum "40GF" {
        description
          "40GF.";
      }
      enum "10GFCOM" {
        description
          "10GFCOM.";
      }
      enum "40GFSPLIT" {
        description
          "40GFSPLIT.";
      }
      enum "Otn" {
        description
          "Otn.";
      }
      enum "ADMCHANNEL" {
        description
          "Channel.";
      }
      enum "ADMPORT" {
        description
          "LinePort.";
      }
      enum "E3" {
        description
          "E3 port.";
      }
      enum "VSR" {
        description
          "VSR port.";
      }
      enum "ATM" {
        description
          "ATM Port.";
      }
    }
    description
      "devmPortType";
  }
  typedef devmPortHardType {
    type enumeration {
      enum "unknown" {
        description
          "Unknown.";
      }
      enum "EthLANPort" {
        description
          "Ethernet LAN Port.";
      }
      enum "EthWANPort" {
        description
          "Ethernet WAN Port.";
      }
      enum "EthGEPort" {
        description
          "Ethernet GE Port.";
      }
      enum "Eth10GEPort" {
        description
          "Ethernet 10GE port.";
      }
      enum "EthGFPort" {
        description
          "Ethernet GF Port.";
      }
      enum "Eth10GFPort" {
        description
          "Ethernet 10GF port.";
      }
      enum "Eth40GFPort" {
        description
          "Ethernet 40GF port.";
      }
      enum "Eth10GFCOMPort" {
        description
          "Ethernet 10GF Com Port.";
      }
      enum "Eth40GFSPLITPort" {
        description
          "Ethernet 40GF Split Port.";
      }
      enum "EthFEPort" {
        description
          "Ethernet FE Port.";
      }
      enum "EthMGEPort" {
        description
          "Ethernet MGE Port.";
      }
      enum "PosPort" {
        description
          "Pos port.";
      }
      enum "OtnPort" {
        description
          "Otn port.";
      }
      enum "CposPort" {
        description
          "Cpos port.";
      }
      enum "E1Port" {
        description
          "E1 port.";
      }
      enum "EthClusterPort" {
        description
          "Ethernet Cluster port for chassis link.";
      }
      enum "ADMCHANNEL" {
        description
          "Channel.";
      }
      enum "ADMLINEPORT" {
        description
          "LinePort.";
      }
      enum "E3Port" {
        description
          "E3 port.";
      }
      enum "AtmPort" {
        description
          "Atm Port.";
      }
      enum "SfpClusterPort" {
        description
          "Optival Cluster port for chassis link.";
      }
      enum "VSRPort" {
        description
          "VSR port.";
      }
    }
    description
      "devmPortHardType";
  }
  typedef devmCardHardType {
    type enumeration {
      enum "unknown" {
        description
          "Unknown card.";
      }
      enum "ETH_20xGF_T_CARD" {
        description
          "ETH_20xGF_T_CARD.";
      }
      enum "ETH_2x10G_10GF_B_CARD" {
        description
          "ETH_2x10G_10GF_B_CARD.";
      }
      enum "ETH_1x10G_11GF_B_CARD" {
        description
          "ETH_1x10G_11GF_B_CARD.";
      }
      enum "FLEX_POS_10G_CARD" {
        description
          "FLEX_POS_10G_CARD.";
      }
      enum "FLEX_POS_2X2.5G_CARD" {
        description
          "FLEX_POS_2X2.5G_CARD.";
      }
      enum "FLEX_POS_4X2.5G_CARD" {
        description
          "FLEX_POS_4X2.5G_CARD.";
      }
      enum "FLEX_POS_8X622M_CARD" {
        description
          "FLEX_POS_8X622M_CARD.";
      }
      enum "ETH_3x40GC_B_CARD" {
        description
          "ETH_3x40GC_B_CARD.";
      }
      enum "POS_2x10GX_CARD" {
        description
          "POS_2x10GX_CARD.";
      }
      enum "ETH_4x10G_12GF_B_CARD" {
        description
          "ETH_4x10G_12GF_B_CARD.";
      }
      enum "OTN_1x40GC_CARD" {
        description
          "OTN_1x40GC_CARD.";
      }
      enum "OTN_12x10GF_CARD" {
        description
          "OTN_12x10GF_CARD.";
      }
      enum "OTN_6x10GF_CARD" {
        description
          "OTN_6x10GF_CARD.";
      }
      enum "FLEX_24XCE1CT1_CARD" {
        description
          "FLEX_24XCE1CT1_CARD.";
      }
      enum "FLEX_2XCPOS_CARD" {
        description
          "FLEX_2XCPOS_CARD.";
      }
      enum "FLEX_4XCPOS_CARD" {
        description
          "FLEX_4XCPOS_CARD.";
      }
      enum "FLEX_8XCPOS_CARD" {
        description
          "FLEX_8XCPOS_CARD.";
      }
      enum "LAN_WAN_2x10GF_T_CARD" {
        description
          "LAN_WAN_2x10GF_T_CARD.";
      }
      enum "LAN_WAN_5x10GF_T_CARD" {
        description
          "LAN_WAN_5x10GF_T_CARD.";
      }
      enum "ETH_24xGF_T_CARD" {
        description
          "ETH_24xGF_T_CARD.";
      }
      enum "ETH_48xGF_B_CARD" {
        description
          "ETH_48xGF_B_CARD.";
      }
      enum "ETH_2x10G_32GF_B_CARD" {
        description
          "ETH_2x10G_32GF_B_CARD.";
      }
      enum "FLEX_ETH_8XGF_B_CARD" {
        description
          "FLEX_ETH_8XGF_B_CARD.";
      }
      enum "ETH_LAN_WAN_2X10G_CARD" {
        description
          "ETH_LAN_WAN_2X10G_CARD.";
      }
      enum "ETH_1x10G_16GF_B_CARD" {
        description
          "ETH_1x10G_16GF_B_CARD.";
      }
      enum "FLEX_POS_8X155M_CARD" {
        description
          "FLEX_POS_8X155M_CARD.";
      }
      enum "FLEX_POS_4X155M_CARD" {
        description
          "FLEX_POS_4X155M_CARD.";
      }
      enum "FLEX_POS_2X155M_CARD" {
        description
          "FLEX_POS_2X155M_CARD.";
      }
      enum "ETH_20xGE_B_CARD" {
        description
          "ETH_20xGE_B_CARD.";
      }
      enum "ETH_20xGE_CARD" {
        description
          "ETH_20xGE_CARD.";
      }
      enum "LAN_2x10GF_ETH_24xGF_CARD" {
        description
          "LAN_2x10GF_ETH_24xGF_CARD.";
      }
      enum "LAN_4x10GF_ETH_40xGF_CARD" {
        description
          "LAN_4x10GF_ETH_40xGF_CARD.";
      }
      enum "ETH_4xFE_B_2xAUX_CARD" {
        description
          "ETH_4xFE_B_2xAUX_CARD.";
      }
      enum "LAN_WAN_2x10GXC_CARD" {
        description
          "LAN_WAN_2x10GXC_CARD.";
      }
      enum "ETH_8xGED_CARD" {
        description
          "ETH_8xGED_CARD.";
      }
      enum "LAN_10GF_ETH_8xGFB_CARD" {
        description
          "LAN_10GF_ETH_8xGFB_CARD.";
      }
      enum "LAN_WAN_4x10GXD_CARD" {
        description
          "LAN_WAN_4x10GXD_CARD.";
      }
      enum "ETH_10xGFD_CARD" {
        description
          "ETH_10xGFD_CARD.";
      }
      enum "ETH_10G_WAN" {
        description
          "ETH_10G_WAN.";
      }
      enum "ETH_10G_LAN" {
        description
          "ETH_10G_LAN.";
      }
      enum "ETH_8x100G_CARD" {
        description
          "ETH_8x100G_CARD.";
      }
      enum "ETH_24x40G_CARD" {
        description
          "ETH_24x40G_CARD.";
      }
      enum "LAN_WAN_60x10GF_CARD" {
        description
          "LAN_WAN_60x10GF_CARD.";
      }
      enum "ETH_10XGE_CARD" {
        description
          "ETH_10XGE_CARD.";
      }
      enum "POS_4X2.5G_CARD" {
        description
          "POS_4X2.5G_CARD.";
      }
      enum "POS_1X10G_CARD" {
        description
          "POS_1X10G_CARD.";
      }
      enum "POS_4X622M_CARD" {
        description
          "POS_4X622M_CARD.";
      }
      enum "ETH_2X10G_LAN_CARD" {
        description
          "ETH_2X10G_LAN_CARD.";
      }
      enum "ETH_2X10G_WAN_CARD" {
        description
          "ETH_2X10G_WAN_CARD.";
      }
      enum "ETH_48XGE_CARD" {
        description
          "ETH_48XGE_CARD.";
      }
      enum "POS_8X155M_CARD" {
        description
          "POS_8X155M_CARD.";
      }
      enum "ETH_24XGE_CARD" {
        description
          "ETH_24XGE_CARD.";
      }
      enum "POS_1X2.5G_CARD" {
        description
          "POS_1X2.5G_CARD.";
      }
      enum "POS_2X2.5G_CARD" {
        description
          "POS_2X2.5G_CARD.";
      }
      enum "POS_2X10G_CARD" {
        description
          "POS_2X10G_CARD.";
      }
      enum "POS_4X155M_CARD" {
        description
          "POS_4X155M_CARD.";
      }
      enum "ETH_5XGE_CARD" {
        description
          "ETH_5XGE_CARD.";
      }
      enum "P1MZ_CARD" {
        description
          "P1MZ_CARD.";
      }
      enum "D1MV_CARD" {
        description
          "D1MV_CARD.";
      }
      enum "ETH_LAN_WAN_4X10G_CARD" {
        description
          "ETH_LAN_WAN_4X10G_CARD.";
      }
      enum "LAN_WAN_2x10GX_CARD" {
        description
          "LAN_WAN_2x10GX_CARD.";
      }
      enum "ETH_2x10GX_CARD" {
        description
          "ETH_2x10GX_CARD.";
      }
      enum "OTN_2x10GX_CARD" {
        description
          "OTN_2x10GX_CARD.";
      }
      enum "LAN_WAN_5x10GX_CARD" {
        description
          "LAN_WAN_5x10GX_CARD.";
      }
      enum "ETH_5x10GX_CARD" {
        description
          "ETH_5x10GX_CARD.";
      }
      enum "POS_40GZ_CARD" {
        description
          "POS_40GZ_CARD.";
      }
      enum "ETH_24xGF_CARD" {
        description
          "ETH_24xGF_CARD.";
      }
      enum "OFCA_CARD" {
        description
          "OFCA_CARD.";
      }
      enum "OFCV_CARD" {
        description
          "OFCV_CARD.";
      }
      enum "OFC40_CARD" {
        description
          "OFC40_CARD.";
      }
      enum "OFC100B_CARD" {
        description
          "OFC100B_CARD.";
      }
      enum "OFC400A_CARD" {
        description
          "OFC400A_CARD.";
      }
      enum "OFC1TA_CARD" {
        description
          "OFC1TA_CARD.";
      }
      enum "OFC400B_CARD" {
        description
          "OFC400B_CARD.";
      }
      enum "OFC1TB_CARD" {
        description
          "OFC1TB_CARD.";
      }
      enum "OFC1TC_CARD" {
        description
          "OFC1TC_CARD.";
      }
      enum "OFC1TD_CARD" {
        description
          "OFC1TD_CARD.";
      }
      enum "OFC400D_CARD" {
        description
          "OFC400D_CARD.";
      }
      enum "OFC100A_CARD" {
        description
          "OFC100A_CARD.";
      }
      enum "OFCB_CARD" {
        description
          "OFCB_CARD.";
      }
      enum "POS_10G_CARD" {
        description
          "POS_10G_CARD.";
      }
      enum "POS_40G_CARD" {
        description
          "POS_40G_CARD.";
      }
      enum "WDM_40G_CARD" {
        description
          "WDM_40G_CARD.";
      }
      enum "ETH_40XGE_SFP_CARD" {
        description
          "ETH_40XGE_SFP_CARD.";
      }
      enum "ETH_40GC_CARD" {
        description
          "ETH_40GC_CARD.";
      }
      enum "ETH_2x100GC_CARD" {
        description
          "ETH_2x100GC_CARD.";
      }
      enum "LAN_WAN_20x10GX_CARD" {
        description
          "LAN_WAN_20x10GX_CARD.";
      }
      enum "ETH_6x40GC_CARD" {
        description
          "ETH_6x40GC_CARD.";
      }
      enum "ETH_1x100GC_CARD" {
        description
          "ETH_1x100GC_CARD.";
      }
      enum "LAN_WAN_24x10GX_CARD" {
        description
          "LAN_WAN_24x10GX_CARD.";
      }
      enum "LAN_WAN_5x10GXB_CARD" {
        description
          "LAN_WAN_5x10GXB_CARD.";
      }
      enum "ETH_5x10GXB_CARD" {
        description
          "ETH_5x10GXB_CARD.";
      }
      enum "POS_8x2.5G_CARD" {
        description
          "POS_8x2.5G_CARD.";
      }
      enum "FLEX_1xCPOS_CARD" {
        description
          "FLEX_1xCPOS_CARD.";
      }
      enum "ETH_5x40GC_CARD" {
        description
          "ETH_5x40GC_CARD.";
      }
      enum "SPU" {
        description
          "SPU.";
      }
      enum "TSUA" {
        description
          "TSUA.";
      }
      enum "LAN_WAN_10x10GX_CARD" {
        description
          "LAN_WAN_10x10GX_CARD.";
      }
      enum "ETH_8xGFC_CARD" {
        description
          "ETH_8xGFC_CARD.";
      }
      enum "ETH_8xGE_CARD" {
        description
          "ETH_8xGE_CARD.";
      }
      enum "FLEX_4xCPOS_CARD" {
        description
          "FLEX_4xCPOS_CARD.";
      }
      enum "FLEX_32xMIE1_CARD" {
        description
          "FLEX_32xMIE1_CARD.";
      }
      enum "FLEX_32xMIE1B_CARD" {
        description
          "FLEX_32xMIE1B_CARD.";
      }
      enum "FLEX_16xMDE1A_CARD" {
        description
          "FLEX_16xMDE1A_CARD.";
      }
      enum "FLEX_16xMDE1B_CARD" {
        description
          "FLEX_16xMDE1B_CARD.";
      }
      enum "POS_4x155MFA_CARD" {
        description
          "POS_4x155MFA_CARD.";
      }
      enum "LAN_WAN_4x10GF_CARD" {
        description
          "LAN_WAN_4x10GF_CARD.";
      }
      enum "ETH_4x10GF_CARD" {
        description
          "ETH_4x10GF_CARD.";
      }
      enum "LAN_10GF_ETH_8xGF_CARD" {
        description
          "LAN_10GF_ETH_8xGF_CARD.";
      }
      enum "ETH_24xGF_B_CARD" {
        description
          "ETH_24xGF_B_CARD.";
      }
      enum "LAN_WAN_12x10GF_B_CARD" {
        description
          "LAN_WAN_12x10GF_B_CARD.";
      }
      enum "ETH_1x100GC_B_CARD" {
        description
          "ETH_1x100GC_B_CARD.";
      }
      enum "LAN_WAN_10x10GF_B_CARD" {
        description
          "LAN_WAN_10x10GF_B_CARD.";
      }
      enum "WDM_2x100GC_CARD" {
        description
          "WDM_2x100GC_CARD.";
      }
      enum "ETH_1x40GC_B_CARD" {
        description
          "ETH_1x40GC_B_CARD.";
      }
      enum "LAN_WAN_6x10GF_B_CARD" {
        description
          "LAN_WAN_6x10GF_B_CARD.";
      }
      enum "LAN_WAN_5x10GF_B_CARD" {
        description
          "LAN_WAN_5x10GF_B_CARD.";
      }
      enum "LAN_WAN_4x10GF_B_CARD" {
        description
          "LAN_WAN_4x10GF_B_CARD.";
      }
      enum "LAN_WAN_3x10GF_B_CARD" {
        description
          "LAN_WAN_3x10GF_B_CARD.";
      }
      enum "ADM" {
        description
          "ADM.";
      }
      enum "ETH_24x40GC_CARD" {
        description
          "ETH_24x40GC_CARD.";
      }
      enum "OFC400C_CARD" {
        description
          "OFC400C_CARD.";
      }
      enum "FLEX_4xE3CT3_CARD" {
        description
          "FLEX_4xE3CT3_CARD.";
      }
      enum "ETH_2x100GC_T_CARD" {
        description
          "ETH_2x100GC_T_CARD.";
      }
      enum "LAN_WAN_24x10GF_T_CARD" {
        description
          "LAN_WAN_24x10GF_T_CARD.";
      }
      enum "LAN_WAN_2x10GF_B_CARD" {
        description
          "LAN_WAN_2x10GF_B_CARD.";
      }
      enum "POS_4x155MF_CARD" {
        description
          "POS_4x155MF_CARD.";
      }
      enum "POS_2x622MF_CARD" {
        description
          "POS_2x622MF_CARD.";
      }
      enum "POS_2x155MF_CARD" {
        description
          "POS_2x155MF_CARD.";
      }
      enum "POS_622MF_CARD" {
        description
          "POS_622MF_CARD.";
      }
      enum "DVSU_SP_CARD" {
        description
          "DVSU_SP_CARD.";
      }
      enum "OTN_4x10GF_CARD" {
        description
          "OTN_4x10GF_CARD.";
      }
      enum "OTN_2x100GF_CARD" {
        description
          "OTN_2x100GF_CARD.";
      }
      enum "OTN_1x100GF_CARD" {
        description
          "OTN_1x100GF_CARD.";
      }
      enum "LAN_WAN_10x10GF_T_CARD" {
        description
          "LAN_WAN_10x10GF_T_CARD";
      }
      enum "FLEX_ATM_2x155M_CARD" {
        description
          "FLEX_ATM_2x155M_CARD.";
      }
      enum "ETH_8x100GC_CARD" {
        description
          "ETH_8x100GC_CARD.";
      }
      enum "ETH_8x100GF_LW_16x10GF" {
        description
          "ETH_8x100GF_LW_16x10GF.";
      }
      enum "ETH_16x100GF_CARD" {
        description
          "ETH_16x100GF_CARD.";
      }
      enum "ETH_16x100GF_LW_32x10GF" {
        description
          "ETH_16x100GF_LW_32x10GF.";
      }
      enum "ETH_10xGF_T_CARD" {
        description
          "ETH_10xGF_T_CARD.";
      }
      enum "LAN_WAN_5x10GF_H_CARD" {
        description
          "LAN_WAN_5x10GF_H_CARD.";
      }
      enum "LAN_WAN_2x10GF_H_CARD" {
        description
          "LAN_WAN_2x10GF_H_CARD.";
      }
      enum "LAN_WAN_2x10GF_I_CARD" {
        description
          "LAN_WAN_2x10GF_I_CARD.";
      }
      enum "LAN_WAN_5x10GF_I_CARD" {
        description
          "LAN_WAN_5x10GF_I_CARD.";
      }
      enum "ETH_100GC_CARD" {
        description
          "ETH_100GC_CARD.";
      }
      enum "LAN_WAN_10x10GF_CARD" {
        description
          "LAN_WAN_10x10GF_CARD.";
      }
      enum "LAN_WAN_20x10GF_T_CARD" {
        description
          "LAN_WAN_20x10GF_T_CARD.";
      }
      enum "ETH_8x100GF_A_CARD" {
        description
          "ETH_8x100GF_A_CARD.";
      }
      enum "LAN_28x10GF_CARD(COMBO)" {
        description
          "LAN_28x10GF_CARD(COMBO).";
      }
      enum "WDM_8x100GC_CARD" {
        description
          "WDM_8x100GC_CARD.";
      }
      enum "ETH_2x100GF_LW_20x10GF" {
        description
          "ETH_2x100GF_LW_20x10GF.";
      }
      enum "LAN_WAN_24x10GF_CARD" {
        description
          "LAN_WAN_24x10GF_CARD.";
      }
      enum "ETH_4x100GF_CARD" {
        description
          "ETH_4x100GF_CARD.";
      }
      enum "OTN_4x100GF_CARD" {
        description
          "OTN_4x100GF_CARD.";
      }
      enum "LAN_WAN_48x10GF_CARD" {
        description
          "LAN_WAN_48x10GF_CARD.";
      }
      enum "ETH_24xGF_H_CARD" {
        description
          "ETH_24xGF_H_CARD.";
      }
      enum "ETH_1x100GC_F_CARD" {
        description
          "ETH_1x100GC_F_CARD.";
      }
      enum "ETH_1x100GB_A_CARD" {
        description
          "ETH_1x100GB_A_CARD.";
      }
      enum "ETH_2x100GB_B_CARD" {
        description
          "ETH_2x100GB_B_CARD.";
      }
      enum "ETH_2x100GB_A_CARD" {
        description
          "ETH_2x100GB_A_CARD.";
      }
      enum "ADM_1xLINE_8xMD_CARD" {
        description
          "ADM_1xLINE_8xMD_CARD.";
      }
      enum "LAN_WAN_6x10GF_I_CARD" {
        description
          "LAN_WAN_6x10GF_I_CARD.";
      }
      enum "LAN_WAN_12x10GF_T_CARD" {
        description
          "LAN_WAN_12x10GF_T_CARD.";
      }
      enum "POS_4X10G_CARD" {
        description
          "POS_4X10G_CARD.";
      }
    }
    description
      "devmCardHardType";
  }
  typedef devmEthPortMediumType {
    type enumeration {
      enum "notSupported" {
        description
          "Unsupported Type.";
      }
      enum "copper" {
        description
          "Copper.";
      }
      enum "fiber" {
        description
          "Fiber.";
      }
    }
    description
      "";
  }
  typedef devmGFEthPortMediumType {
    type enumeration {
      enum "fiber100" {
        description
          "";
      }
      enum "fiber1000" {
        description
          "";
      }
    }
    description
      "";
  }
  typedef devmDuplex {
    type enumeration {
      enum "half" {
        description
          "Half-duplex.";
      }
      enum "full" {
        description
          "Full-duplex.";
      }
      enum "auto" {
        description
          "Auto.";
      }
    }
    description
      "devmDuplex";
  }
  typedef devmTransMode {
    type enumeration {
      enum "unknown" {
        description
          "Unknown.";
      }
      enum "multiMode" {
        description
          "Multi-mode.";
      }
      enum "singleMode" {
        description
          "Single Mode.";
      }
      enum "copperMode" {
        description
          "Copper Mode.";
      }
    }
    description
      "devmTransMode";
  }
  typedef devmHardType {
    type enumeration {
      enum "unknown" {
        description
          "Not Equipped.";
      }
      enum "CR2D00EEGF10" {
        description
          "CR2D00EEGF10.";
      }
      enum "CR5D00EEGF70" {
        description
          "CR5D00EEGF70.";
      }
      enum "CR57E8NCB0" {
        description
          "CR57E8NCB0.";
      }
      enum "ME0D00E8GE71" {
        description
          "ME0D00E8GE71.";
      }
      enum "ME0D00EAGF70" {
        description
          "ME0D00EAGF70.";
      }
      enum "ME0D00L4XF72" {
        description
          "ME0D00L4XF72.";
      }
      enum "ME0DL1XE8G71" {
        description
          "ME0DL1XE8G71.";
      }
      enum "ME0D00L2XF71" {
        description
          "ME0D00L2XF71.";
      }
      enum "ME0D00L4XF70" {
        description
          "ME0D00L4XF70.";
      }
      enum "ME0DL1XE8G70" {
        description
          "ME0DL1XE8G70.";
      }
      enum "ME0D00L2XF70" {
        description
          "ME0D00L2XF70.";
      }
      enum "ME0D00E8GF71" {
        description
          "ME0D00E8GF71.";
      }
      enum "ME0D00E8GE70" {
        description
          "ME0D00E8GE70.";
      }
      enum "ME0D00C4CF71" {
        description
          "ME0D00C4CF71.";
      }
      enum "ME0D000IE170" {
        description
          "ME0D000IE170.";
      }
      enum "ME0D000IE171" {
        description
          "ME0D000IE171.";
      }
      enum "ME0D000DE170" {
        description
          "ME0D000DE170.";
      }
      enum "ME0D000DE171" {
        description
          "ME0D000DE171.";
      }
      enum "ME0D00P4CF70" {
        description
          "ME0D00P4CF70.";
      }
      enum "ME0DP2C1HF70" {
        description
          "ME0DP2C1HF70.";
      }
      enum "ME0D00AUXQ10" {
        description
          "ME0D00AUXQ10.";
      }
      enum "ME0D08CWDM70" {
        description
          "ME0D08CWDM70.";
      }
      enum "ME0D00C4T370" {
        description
          "ME0D00C4T370.";
      }
      enum "ME0D0EAGFH70" {
        description
          "ME0D0EAGFH70.";
      }
      enum "ME0D0L2XFH71" {
        description
          "ME0D0L2XFH71.";
      }
      enum "ME2D00E8GE12" {
        description
          "ME2D00E8GE12.";
      }
      enum "ME2D00EAGF10" {
        description
          "ME2D00EAGF10.";
      }
      enum "ME2D00L4XF11" {
        description
          "ME2D00L4XF11.";
      }
      enum "ME2DL1XE8G11" {
        description
          "ME2DL1XE8G11.";
      }
      enum "ME2D00L2XF12" {
        description
          "ME2D00L2XF12.";
      }
      enum "CR5D00P2XX72" {
        description
          "CR5D00P2XX72.";
      }
      enum "CR57L4XEBG0" {
        description
          "CR57L4XEBG0.";
      }
      enum "CR57TBXF00" {
        description
          "CR57TBXF00.";
      }
      enum "CR57T6XF00" {
        description
          "CR57T6XF00.";
      }
      enum "CR5D00T1MC60" {
        description
          "CR5D00T1MC60.";
      }
      enum "CR5D00TBXF70" {
        description
          "CR5D00TBXF70.";
      }
      enum "CX6D00MPUD11" {
        description
          "CX6D00MPUD11.";
      }
      enum "CX6D0SRUA611" {
        description
          "CX6D0SRUA611.";
      }
      enum "CX6DSFUIA07C" {
        description
          "CX6DSFUIA07C.";
      }
      enum "CX6DL2XEIG1B" {
        description
          "CX6DL2XEIG1B.";
      }
      enum "CX6DL4XEBG1B" {
        description
          "CX6DL4XEBG1B.";
      }
      enum "CX6D0L5XFA11" {
        description
          "CX6D0L5XFA11.";
      }
      enum "CR5D0EFGFA73" {
        description
          "CR5D0EFGFA73.";
      }
      enum "CR5DL1XEDG70" {
        description
          "CR5DL1XEDG70.";
      }
      enum "CX6D0LAXFA11" {
        description
          "CX6D0LAXFA11.";
      }
      enum "CX6DISUF5010" {
        description
          "CX6DISUF5010.";
      }
      enum "CR5DLPUF5071" {
        description
          "CR5DLPUF5071.";
      }
      enum "CR5DLPUF507M" {
        description
          "CR5DLPUF507M.";
      }
      enum "CX6DISUF5011" {
        description
          "CX6DISUF5011.";
      }
      enum "CX6DL1XEDG1A" {
        description
          "CX6DL1XEDG1A.";
      }
      enum "CX6D0EFGFA12" {
        description
          "CX6D0EFGFA12.";
      }
      enum "CX6D0EMGFA10" {
        description
          "CX6D0EMGFA10.";
      }
      enum "ME0DMSUFF070" {
        description
          "ME0DMSUFF070.";
      }
      enum "CR5D00E2NC76" {
        description
          "CR5D00E2NC76.";
      }
      enum "CR5D00LEXF76" {
        description
          "CR5D00LEXF76.";
      }
      enum "CR5DE1NLAX76" {
        description
          "CR5DE1NLAX76.";
      }
      enum "CR5D00E2NC75" {
        description
          "CR5D00E2NC75.";
      }
      enum "CR5D00LEXF75" {
        description
          "CR5D00LEXF75.";
      }
      enum "CR5DLPUFE07B" {
        description
          "CR5DLPUFE07B.";
      }
      enum "CR5DE1NLAX75" {
        description
          "CR5DE1NLAX75.";
      }
      enum "CR5D0E6MFA70" {
        description
          "CR5D0E6MFA70.";
      }
      enum "CR5D0E6MFA71" {
        description
          "CR5D0E6MFA71.";
      }
      enum "CR5D00T6XF70" {
        description
          "CR5D00T6XF70.";
      }
      enum "CR53CFE10" {
        description
          "CR53CFE10.";
      }
      enum "CR5D00C2CF70" {
        description
          "CR5D00C2CF70.";
      }
      enum "CR5D00C4CF70" {
        description
          "CR5D00C4CF70.";
      }
      enum "CR5D00C8CF71" {
        description
          "CR5D00C8CF71.";
      }
      enum "CX6D00C8CF10" {
        description
          "CX6D00C8CF10.";
      }
      enum "CX6D0L2XFA10" {
        description
          "CX6D0L2XFA10.";
      }
      enum "CR57L3XFB0" {
        description
          "CR57L3XFB0.";
      }
      enum "CR57L2XFB2" {
        description
          "CR57L2XFB2.";
      }
      enum "CR57L4XFB2" {
        description
          "CR57L4XFB2.";
      }
      enum "CR57EFGFC0" {
        description
          "CR57EFGFC0.";
      }
      enum "CR57L1XEDG0" {
        description
          "CR57L1XEDG0.";
      }
      enum "ME0D0LBXXB7H" {
        description
          "ME0D0LBXXB7H.";
      }
      enum "ME0D2L1NXB7H" {
        description
          "ME0D2L1NXB7H.";
      }
      enum "ME0D0L1NXB7H" {
        description
          "ME0D0L1NXB7H.";
      }
      enum "CX6D0E2NCA10" {
        description
          "CX6D0E2NCA10.";
      }
      enum "CX6D0LFXFA11" {
        description
          "CX6D0LFXFA11.";
      }
      enum "ME0D0LAXFE7H" {
        description
          "ME0D0LAXFE7H.";
      }
      enum "ME0D0LAXFB7H" {
        description
          "ME0D0LAXFB7H.";
      }
      enum "ME0D0LAXFH7H" {
        description
          "ME0D0LAXFH7H.";
      }
      enum "CR57LAXFB1" {
        description
          "CR57LAXFB1.";
      }
      enum "CR57L5XFB2" {
        description
          "CR57L5XFB2.";
      }
      enum "CR57EMGFC0" {
        description
          "CR57EMGFC0.";
      }
      enum "CR57L2XEIG0" {
        description
          "CR57L2XEIG0.";
      }
      enum "CR57L5XFC0" {
        description
          "CR57L5XFC0.";
      }
      enum "ME0D0L5XXE7H" {
        description
          "ME0D0L5XXE7H.";
      }
      enum "ME0D0L6XXB7H" {
        description
          "ME0D0L6XXB7H.";
      }
      enum "ME0D0L2XXE7H" {
        description
          "ME0D0L2XXE7H.";
      }
      enum "ME0D0L5XXE7F" {
        description
          "ME0D0L5XXE7F.";
      }
      enum "ME0D0EFGFE7H" {
        description
          "ME0D0EFGFE7H.";
      }
      enum "ME0D0L2XXB7H" {
        description
          "ME0D0L2XXB7H.";
      }
      enum "ME0D0L5XXB7F" {
        description
          "ME0D0L5XXB7F.";
      }
      enum "ME0D0L5XXB7H" {
        description
          "ME0D0L5XXB7H.";
      }
      enum "ME0D0EFGFB7H" {
        description
          "ME0D0EFGFB7H.";
      }
      enum "CR57D2NT00" {
        description
          "CR57D2NT00.";
      }
      enum "CR53P8CF0" {
        description
          "CR53P8CF0.";
      }
      enum "CR53P4CF0" {
        description
          "CR53P4CF0.";
      }
      enum "CR5D00P2CF70" {
        description
          "CR5D00P2CF70.";
      }
      enum "CR2D00E1MF70" {
        description
          "CR2D00E1MF70.";
      }
      enum "CR2D00T4XF70" {
        description
          "CR2D00T4XF70.";
      }
      enum "CR5D00E1MF70" {
        description
          "CR5D00E1MF70.";
      }
      enum "CR5D00T4XF70" {
        description
          "CR5D00T4XF70.";
      }
      enum "CR5D00L4XEKGFB71" {
        description
          "CR5D00L4XEKGFB71.";
      }
      enum "CR5D00L2XEFGFA71" {
        description
          "CR5D00L2XEFGFA71.";
      }
      enum "CR5D00AUXQ10" {
        description
          "CR5D00AUXQ10.";
      }
      enum "CR5M0E8GFA30" {
        description
          "CR5M0E8GFA30.";
      }
      enum "CR5D0L2XFA70" {
        description
          "CR5D0L2XFA70.";
      }
      enum "CR5D0L5XFA72" {
        description
          "CR5D0L5XFA72.";
      }
      enum "CR5D0LAXFE70" {
        description
          "CR5D0LAXFE70.";
      }
      enum "CR5D00LAXF70" {
        description
          "CR5D00LAXF70.";
      }
      enum "CR5D0L5XFA70" {
        description
          "CR5D0L5XFA70.";
      }
      enum "CR5D0EEGEA70" {
        description
          "CR5D0EEGEA70.";
      }
      enum "CR5D00P4CF70" {
        description
          "CR5D00P4CF70.";
      }
      enum "CR2D00L2XF12" {
        description
          "CR2D00L2XF12.";
      }
      enum "CX6D00L2XF11" {
        description
          "CX6D00L2XF11.";
      }
      enum "CR5D00L2XF71" {
        description
          "CR5D00L2XF71.";
      }
      enum "CR2D0L2XFH10" {
        description
          "CR2D0L2XFH10.";
      }
      enum "CR5D0L2XFH71" {
        description
          "CR5D0L2XFH71.";
      }
      enum "CR2D00E8GE12" {
        description
          "CR2D00E8GE12.";
      }
      enum "CX6D00E8GE11" {
        description
          "CX6D00E8GE11.";
      }
      enum "CR5D00E8GE71" {
        description
          "CR5D00E8GE71.";
      }
      enum "CR2DL1XE8G11" {
        description
          "CR2DL1XE8G11.";
      }
      enum "CX6DL1XE8G11" {
        description
          "CX6DL1XE8G11.";
      }
      enum "CR5DL1XE8G71" {
        description
          "CR5DL1XE8G71.";
      }
      enum "CR2D00L4XF11" {
        description
          "CR2D00L4XF11.";
      }
      enum "CX6D00L4XF11" {
        description
          "CX6D00L4XF11.";
      }
      enum "CR5D00L4XF71" {
        description
          "CR5D00L4XF71.";
      }
      enum "CR5D00L4XF72" {
        description
          "CR5D00L4XF72.";
      }
      enum "CR5D08CWDM70" {
        description
          "CR5D08CWDM70.";
      }
      enum "CR2D00EAGF10" {
        description
          "CR2D00EAGF10.";
      }
      enum "CX6D00EAGF10" {
        description
          "CX6D00EAGF10.";
      }
      enum "CR5D00EAGF70" {
        description
          "CR5D00EAGF70.";
      }
      enum "CR2D0EAGFH10" {
        description
          "CR2D0EAGFH10.";
      }
      enum "CR5D0EAGFH70" {
        description
          "CR5D0EAGFH70.";
      }
      enum "chassis" {
        description
          "Chassis.";
      }
      enum "boardSlot" {
        description
          "Board slot.";
      }
      enum "mpuSlot" {
        description
          "MPU slot.";
      }
      enum "lpuSlot" {
        description
          "LPU slot.";
      }
      enum "sfuSlot" {
        description
          "SFU slot.";
      }
      enum "icuSlot" {
        description
          "ICU slot.";
      }
      enum "ecuSlot" {
        description
          "ECU slot.";
      }
      enum "clkSlot" {
        description
          "CLK slot.";
      }
      enum "fanSlot" {
        description
          "Fan slot.";
      }
      enum "powerSlot" {
        description
          "Power slot.";
      }
      enum "PmuSlot" {
        description
          "PMU slot.";
      }
      enum "pmuSlot" {
        description
          "PMU slot.";
      }
      enum "picSlot" {
        description
          "Pic slot.";
      }
      enum "ofcSlot" {
        description
          "Ofc slot.";
      }
      enum "lcdSlot" {
        description
          "LCD slot.";
      }
      enum "cfcardSlot" {
        description
          "CF card slot.";
      }
      enum "cmuSlot" {
        description
          "CMU slot.";
      }
      enum "virtualSubSlot" {
        description
          "Virtual sub slot.";
      }
      enum "virtualSlot" {
        description
          "Virtual slot.";
      }
      enum "fname8090Unknown" {
        description
          "Unknown.";
      }
      enum "fname8090Whole" {
        description
          "NE5000E chassis.";
      }
      enum "fname8090NE5000EX" {
        description
          "NE5000EX chassis.";
      }
      enum "fname8090ClusterCentral" {
        description
          "NE5000E cluster central chassis.";
      }
      enum "fname8090NE5000EX-VB" {
        description
          "NE5000EX-VB chassis.";
      }
      enum "fname8090NE5000EX-A" {
        description
          "NE5000EX16A Chassis.";
      }
      enum "fname8090NE5000ENGCCC" {
        description
          "NE5000ENGCCC Chassis.";
      }
      enum "CE585048T4S2QEI" {
        description
          "CE585048T4S2QEI chassis.";
      }
      enum "CE685048S4QEI" {
        description
          "CE685048S4QEI chassis.";
      }
      enum "CE685048T4QEI" {
        description
          "CE685048T4QEI chassis.";
      }
      enum "CR52MPUA" {
        description
          "CR52MPUA.";
      }
      enum "CR52MPUB" {
        description
          "CR52MPUB.";
      }
      enum "CR55MPUA" {
        description
          "CR55MPUA.";
      }
      enum "CR55MPUAB" {
        description
          "CR55MPUAB.";
      }
      enum "CR56RPUA" {
        description
          "CR56RPUA.";
      }
      enum "CR52LPUA" {
        description
          "CR52LPUA.";
      }
      enum "CR57E8NC" {
        description
          "CR57E8NC.";
      }
      enum "CR52LPUB" {
        description
          "CR52LPUB.";
      }
      enum "CR52LPUC" {
        description
          "CR52LPUC.";
      }
      enum "CR52LPUE" {
        description
          "CR52LPUE.";
      }
      enum "CR52LPUR" {
        description
          "CR52LPUR.";
      }
      enum "CR52LPUF" {
        description
          "CR52LPUF.";
      }
      enum "CR52LPUG" {
        description
          "CR52LPUG.";
      }
      enum "CR52LPUH" {
        description
          "CR52LPUH.";
      }
      enum "CR52LPUI" {
        description
          "CR52LPUI.";
      }
      enum "CR52LPUK" {
        description
          "CR52LPUK.";
      }
      enum "CR52LPUM" {
        description
          "CR52LPUM.";
      }
      enum "CR52LPUN" {
        description
          "CR52LPUN.";
      }
      enum "CR52SPUC" {
        description
          "CR52SPUC.";
      }
      enum "CR56LPUF100A" {
        description
          "CR56LPUF100A.";
      }
      enum "CR56LPUF100B" {
        description
          "CR56LPUF100B.";
      }
      enum "CR56LPUI100A" {
        description
          "CR56LPUI100A.";
      }
      enum "CR56LPUI100B" {
        description
          "CR56LPUI100B.";
      }
      enum "CR56LPUI100C" {
        description
          "CR56LPUI100C.";
      }
      enum "CR56LPUF200A" {
        description
          "CR56LPUF200A.";
      }
      enum "RNRLPUB" {
        description
          "RNRLPUB.";
      }
      enum "RNRLPUD" {
        description
          "RNRLPUD.";
      }
      enum "RNRLPUF" {
        description
          "RNRLPUF.";
      }
      enum "RNRNS" {
        description
          "RNRNS.";
      }
      enum "RNRGRE" {
        description
          "RNRGRE.";
      }
      enum "CR52SFUA" {
        description
          "CR52SFUA.";
      }
      enum "CR52SRUA" {
        description
          "CR52SRUA.";
      }
      enum "CR52SFUD" {
        description
          "CR52SFUD.";
      }
      enum "CR52SFUF" {
        description
          "CR52SFUF.";
      }
      enum "CR52SFUG" {
        description
          "CR52SFUG.";
      }
      enum "CR52SFUC" {
        description
          "CR52SFUC.";
      }
      enum "CR52SFEA" {
        description
          "CR52SFEA.";
      }
      enum "CR52K-SFEA" {
        description
          "CR52K-SFEA.";
      }
      enum "CR55SFUA" {
        description
          "CR55SFUA.";
      }
      enum "CR55ECUA" {
        description
          "CR55ECUA.";
      }
      enum "CR55C-ECUA" {
        description
          "CR55C-ECUA.";
      }
      enum "CR55ICUA" {
        description
          "CR55ICUA.";
      }
      enum "CR56SFUF100B" {
        description
          "CR56SFUF100B.";
      }
      enum "CR55SFUI100A" {
        description
          "CR55SFUI100A.";
      }
      enum "CR56SFUF100C" {
        description
          "CR56SFUF100C.";
      }
      enum "CR56SFU200A" {
        description
          "CR56SFU200A.";
      }
      enum "CR56SFU400A" {
        description
          "CR56SFU400A.";
      }
      enum "CR55MPUA5" {
        description
          "CR55MPUA5.";
      }
      enum "CR55ICUB" {
        description
          "CR55ICUB.";
      }
      enum "CR55SFUF400A" {
        description
          "CR55SFUF400A.";
      }
      enum "CR55SFUI400B" {
        description
          "CR55SFUI400B.";
      }
      enum "CR55SFUI400C" {
        description
          "CR55SFUI400C.";
      }
      enum "CR55ECU100A" {
        description
          "CR55ECU100A.";
      }
      enum "CR52SFEB" {
        description
          "CR52SFEB.";
      }
      enum "DE51SRU1A" {
        description
          "DE51SRU1A.";
      }
      enum "DE51SRU1B" {
        description
          "DE51SRU1B.";
      }
      enum "DE51SRU1C" {
        description
          "DE51SRU1C.";
      }
      enum "CR5DSFUFA06C" {
        description
          "CR5DSFUFA06C.";
      }
      enum "CR5DSFUIK06A" {
        description
          "CR5DSFUIK06A.";
      }
      enum "CR5D0MPUA550" {
        description
          "CR5D0MPUA550.";
      }
      enum "CR5D00ICUB50" {
        description
          "CR5D00ICUB50.";
      }
      enum "CR5DSFUFK050" {
        description
          "CR5DSFUFK050.";
      }
      enum "CR5D0MPUA451" {
        description
          "CR5D0MPUA451.";
      }
      enum "CR5D00ICUA51" {
        description
          "CR5D00ICUA51.";
      }
      enum "CR9D0MPUN180" {
        description
          "CR9D0MPUN180.";
      }
      enum "CR9D00E8NC80" {
        description
          "CR9D00E8NC80.";
      }
      enum "CR9D00EFMB80" {
        description
          "CR9D00EFMB80.";
      }
      enum "CR9D0SFUTF80" {
        description
          "CR9D0SFUTF80.";
      }
      enum "CR9D00EPXF80" {
        description
          "CR9D00EPXF80.";
      }
      enum "CR9D00EDNB80" {
        description
          "CR9D00EDNB80.";
      }
      enum "CR9D000CMU60" {
        description
          "CR9D000CMU60.";
      }
      enum "CR9D00D8NC80" {
        description
          "CR9D00D8NC80.";
      }
      enum "CR5DSFUFK051" {
        description
          "CR5DSFUFK051.";
      }
      enum "CR5DSFUFT050" {
        description
          "CR5DSFUFT050.";
      }
      enum "CR5DSFUIT06H" {
        description
          "CR5DSFUIT06H.";
      }
      enum "CR5D0MPUA750" {
        description
          "CR5D0MPUA750.";
      }
      enum "CR5D0MPUB660" {
        description
          "CR5D0MPUB660.";
      }
      enum "CR5DSFUIK06B" {
        description
          "CR5DSFUIK06B.";
      }
      enum "CR5DSFUIK06C" {
        description
          "CR5DSFUIK06C.";
      }
      enum "BOOTROM" {
        description
          "BOOTROM.";
      }
      enum "FLASH" {
        description
          "FLASH.";
      }
      enum "EPLD1" {
        description
          "EPLD1.";
      }
      enum "EPLD2" {
        description
          "EPLD2.";
      }
      enum "CR52E1XX" {
        description
          "CR52E1XX.";
      }
      enum "CR52W1XX" {
        description
          "CR52W1XX.";
      }
      enum "CR2D00C1CF11" {
        description
          "CR2D00C1CF11.";
      }
      enum "CR52EAGF" {
        description
          "CR52EAGF.";
      }
      enum "CR52P4UF" {
        description
          "CR52P4UF.";
      }
      enum "CR52P1XX" {
        description
          "CR52P1XX.";
      }
      enum "CR52P4HF" {
        description
          "CR52P4HF.";
      }
      enum "CR52E2XX" {
        description
          "CR52E2XX.";
      }
      enum "CR52W2XX" {
        description
          "CR52W2XX.";
      }
      enum "CR52P2XX" {
        description
          "CR52P2XX.";
      }
      enum "CR52EMGE" {
        description
          "CR52EMGE.";
      }
      enum "CR52P8CF" {
        description
          "CR52P8CF.";
      }
      enum "CR52EFGE" {
        description
          "CR52EFGE.";
      }
      enum "CR52P1UF" {
        description
          "CR52P1UF.";
      }
      enum "CR52P2UF" {
        description
          "CR52P2UF.";
      }
      enum "CR52E5GF" {
        description
          "CR52E5GF.";
      }
      enum "CR52P4CF" {
        description
          "CR52P4CF.";
      }
      enum "CR53P1MZ" {
        description
          "CR53P1MZ.";
      }
      enum "CR52D1MV" {
        description
          "CR52D1MV.";
      }
      enum "CR52E4XX" {
        description
          "CR52E4XX.";
      }
      enum "CR56P2XX" {
        description
          "CR56P2XX.";
      }
      enum "CR56L2XX" {
        description
          "CR56L2XX.";
      }
      enum "CR56E2XX" {
        description
          "CR56E2XX.";
      }
      enum "CR56D2XX" {
        description
          "CR56D2XX.";
      }
      enum "CR56L5XX" {
        description
          "CR56L5XX.";
      }
      enum "CR56E5XX" {
        description
          "CR56E5XX.";
      }
      enum "CR56P1MZ" {
        description
          "CR56P1MZ.";
      }
      enum "CR56E1NC" {
        description
          "CR56E1NC.";
      }
      enum "CR56EFGF" {
        description
          "CR56EFGF.";
      }
      enum "CR52EKGFY" {
        description
          "CR52EKGFY.";
      }
      enum "CR57EFGF" {
        description
          "CR57EFGF.";
      }
      enum "CR56E1NCC" {
        description
          "CR56E1NCC.";
      }
      enum "CR52P1XZ" {
        description
          "CR52P1XZ.";
      }
      enum "CR52E1XZ" {
        description
          "CR52E1XZ.";
      }
      enum "CR52W1XZ" {
        description
          "CR52W1XZ.";
      }
      enum "CR56E2ND" {
        description
          "CR56E2ND.";
      }
      enum "CR56E6MB" {
        description
          "CR56E6MB.";
      }
      enum "CR56LEXF" {
        description
          "CR56LEXF.";
      }
      enum "CR56E1NCB" {
        description
          "CR56E1NCB.";
      }
      enum "CR56LFXF" {
        description
          "CR56LFXF.";
      }
      enum "CR56L5XFB" {
        description
          "CR56L5XFB.";
      }
      enum "CR56E5XFB" {
        description
          "CR56E5XFB.";
      }
      enum "CR56P8UF" {
        description
          "CR56P8UF.";
      }
      enum "CR56E2NCC" {
        description
          "CR56E2NCC.";
      }
      enum "CR56E5MB" {
        description
          "CR56E5MB.";
      }
      enum "SPU" {
        description
          "SPU.";
      }
      enum "TSUA" {
        description
          "TSUA.";
      }
      enum "CR56E1MC" {
        description
          "CR56E1MC.";
      }
      enum "CR56LAXFA" {
        description
          "CR56LAXFA.";
      }
      enum "CR55OFCA" {
        description
          "CR55OFCA.";
      }
      enum "CR57LFXFE" {
        description
          "CR57LFXFE.";
      }
      enum "CR57E2NCE" {
        description
          "CR57E2NCE.";
      }
      enum "CR55C-OFCA" {
        description
          "CR55C-OFCA.";
      }
      enum "CR52OFCB" {
        description
          "CR52OFCB.";
      }
      enum "CR55OFC40" {
        description
          "CR55OFC40.";
      }
      enum "CR55OFC100A" {
        description
          "CR55OFC100A.";
      }
      enum "CR55OFC100B" {
        description
          "CR55OFC100B.";
      }
      enum "CR55OFC400A" {
        description
          "CR55OFC400A.";
      }
      enum "CR5M0OFCK050" {
        description
          "CR5M0OFCK050.";
      }
      enum "CR55OFC1TA" {
        description
          "CR55OFC1TA.";
      }
      enum "CR5D0OFCT050" {
        description
          "CR5D0OFCT050.";
      }
      enum "CR55OFC400D" {
        description
          "CR55OFC400D.";
      }
      enum "CR5D0OFCK051" {
        description
          "CR5D0OFCK051.";
      }
      enum "CR55OFC400B" {
        description
          "CR55OFC400B.";
      }
      enum "CR55OFC1TB" {
        description
          "CR55OFC1TB.";
      }
      enum "CR50OFC1TC" {
        description
          "CR50OFC1TC.";
      }
      enum "CR50OFC1TD" {
        description
          "CR50OFC1TD.";
      }
      enum "CR52OFCV" {
        description
          "CR52OFCV.";
      }
      enum "Eth" {
        description
          "Ethernet port.";
      }
      enum "Pos" {
        description
          "Pos port.";
      }
      enum "GE" {
        description
          "Gigabit Ethernet port.";
      }
      enum "10GE" {
        description
          "10GE.";
      }
      enum "GF" {
        description
          "GF.";
      }
      enum "10GF" {
        description
          "10GF.";
      }
      enum "40GF" {
        description
          "40GF.";
      }
      enum "10GFCOM" {
        description
          "10GFCOM.";
      }
      enum "Cpos" {
        description
          "Cpos port.";
      }
      enum "E1" {
        description
          "E1 port.";
      }
      enum "E3" {
        description
          "E3 port.";
      }
      enum "ATM" {
        description
          "Atm Port.";
      }
      enum "40GFSPLIT" {
        description
          "40GFSPLIT.";
      }
      enum "VSR" {
        description
          "VSR port.";
      }
      enum "FSP" {
        description
          "FSP port.";
      }
      enum "LFE" {
        description
          "LFE.";
      }
      enum "EXTPOWER" {
        description
          "EXTPOWER.";
      }
      enum "POWER" {
        description
          "Power supply.";
      }
      enum "POWER DC" {
        description
          "POWER DC.";
      }
      enum "POWER AC" {
        description
          "POWER AC.";
      }
      enum "PMU" {
        description
          "PMU.";
      }
      enum "PM" {
        description
          "PM.";
      }
      enum "CLOCK" {
        description
          "Clock board.";
      }
      enum "FAN" {
        description
          "Fan.";
      }
      enum "CX67FCBA" {
        description
          "FAN.";
      }
      enum "CX67FCBB" {
        description
          "FAN.";
      }
      enum "CX67FCBB_R" {
        description
          "FAN.";
      }
      enum "CX68FCBC" {
        description
          "FAN.";
      }
      enum "CX68FCBC_NEW" {
        description
          "FAN.";
      }
      enum "CX68FCBD" {
        description
          "FAN.";
      }
      enum "CX68FCBD_R" {
        description
          "FAN.";
      }
      enum "LCD" {
        description
          "LCD.";
      }
      enum "CFCARD" {
        description
          "CF card.";
      }
      enum "CMU" {
        description
          "CMU.";
      }
      enum "CR5D00EKGF60" {
        description
          "CR5D00EKGF60.";
      }
      enum "CR5D00P4XX60" {
        description
          "CR5D00P4XX60.";
      }
      enum "CR5D00P8UF61" {
        description
          "CR5D00P8UF61.";
      }
      enum "CR5D00E4XX60" {
        description
          "CR5D00E4XX60.";
      }
      enum "CR5D00W4XX60" {
        description
          "CR5D00W4XX60.";
      }
      enum "CR5DLPUFA060" {
        description
          "CR5DLPUFA060.";
      }
      enum "CR5D00LEXF60" {
        description
          "CR5D00LEXF60.";
      }
      enum "CR5D00E2NC60" {
        description
          "CR5D00E2NC60.";
      }
      enum "CR5DE1NLAX60" {
        description
          "CR5DE1NLAX60.";
      }
      enum "CR5DSFEBA06B" {
        description
          "CR5DSFEBA06B.";
      }
      enum "CR5D0MPUB461" {
        description
          "CR5D0MPUB461.";
      }
      enum "CR5DSFUFA06B" {
        description
          "CR5DSFUFA06B.";
      }
      enum "CR5DSFUIE060" {
        description
          "CR5DSFUIE060.";
      }
      enum "CR5D0MPUA450" {
        description
          "CR5D0MPUA450.";
      }
      enum "CR5DECUFA050" {
        description
          "CR5DECUFA050.";
      }
      enum "CR5DSFUIA050" {
        description
          "CR5DSFUIA050.";
      }
      enum "CR5D00L5XX60" {
        description
          "CR5D00L5XX60.";
      }
      enum "CR5D00E5XX60" {
        description
          "CR5D00E5XX60.";
      }
      enum "CR5D00L2XX60" {
        description
          "CR5D00L2XX60.";
      }
      enum "CR5D00E2XX60" {
        description
          "CR5D00E2XX60.";
      }
      enum "CR5D00EFGF60" {
        description
          "CR5D00EFGF60.";
      }
      enum "CR5D00P1MZ60" {
        description
          "CR5D00P1MZ60.";
      }
      enum "CR5D00P2XX60" {
        description
          "CR5D00P2XX60.";
      }
      enum "CR5M00E1MC60" {
        description
          "CR5M00E1MC60.";
      }
      enum "CR5D00E1NC60" {
        description
          "CR5D00E1NC60.";
      }
      enum "CR5D00LAXX60" {
        description
          "CR5D00LAXX60.";
      }
      enum "CR5D00E2NC61" {
        description
          "CR5D00E2NC61.";
      }
      enum "CR5D00E6MF61" {
        description
          "CR5D00E6MF61.";
      }
      enum "CR5D00LEXF61" {
        description
          "CR5D00LEXF61.";
      }
      enum "CR5D00E1NC61" {
        description
          "CR5D00E1NC61.";
      }
      enum "CR5D00L5XF60" {
        description
          "CR5D00L5XF60.";
      }
      enum "CR5D00E5XF60" {
        description
          "CR5D00E5XF60.";
      }
      enum "CR5D00P8UF60" {
        description
          "CR5D00P8UF60.";
      }
      enum "CR5D00E2NC62" {
        description
          "CR5D00E2NC62.";
      }
      enum "CR5D00E5MF61" {
        description
          "CR5D00E5MF61.";
      }
      enum "CR5D0OFCA060" {
        description
          "CR5D0OFCA060.";
      }
      enum "other" {
        description
          "Other.";
      }
      enum "CX6D00MPUK70" {
        description
          "CX6D00MPUK70.";
      }
      enum "CX6PM2EBAS70" {
        description
          "CX6PM2EBAS70.";
      }
      enum "CX6PM2EBAS71" {
        description
          "CX6PM2EBAS71.";
      }
      enum "CX6PM2FBAS70" {
        description
          "CX6PM2FBAS70.";
      }
      enum "CX6PM2FBAS71" {
        description
          "CX6PM2FBAS71.";
      }
      enum "CR2P2EBASD10" {
        description
          "CR2P2EBASD10.";
      }
      enum "CR2P2EBASA10" {
        description
          "CR2P2EBASA10.";
      }
      enum "CR2P2FBASD10" {
        description
          "CR2P2FBASD10.";
      }
      enum "CR2P2FBASA10" {
        description
          "CR2P2FBASA10.";
      }
      enum "CR5PM2EBAS70" {
        description
          "CR5PM2EBAS70.";
      }
      enum "CR5PM2EBAS71" {
        description
          "CR5PM2EBAS71.";
      }
      enum "CR5PM2FBAS70" {
        description
          "CR5PM2FBAS70.";
      }
      enum "CR5PM2FBAS71" {
        description
          "CR5PM2FBAS71.";
      }
      enum "TNRPM2EBAS70" {
        description
          "TNRPM2EBAS70.";
      }
      enum "TNRPM2EBAS71" {
        description
          "TNRPM2EBAS71.";
      }
      enum "TNRPM2FBAS70" {
        description
          "TNRPM2FBAS70.";
      }
      enum "TNRPM2FBAS71" {
        description
          "TNRPM2FBAS71.";
      }
      enum "CR5PM2HBAS72" {
        description
          "CR5PM2HBAS72.";
      }
      enum "CR5PM2HBAS73" {
        description
          "CR5PM2HBAS73.";
      }
      enum "CR5B0BKP0377" {
        description
          "CR5B0BKP0377.";
      }
      enum "CX6PM2HBAS72" {
        description
          "CX6PM2HBAS72.";
      }
      enum "CX6PM2HBAS73" {
        description
          "CX6PM2HBAS73.";
      }
      enum "CX6B0BKP0375" {
        description
          "CX6B0BKP0375.";
      }
      enum "CX6D00MPUK10" {
        description
          "CX6D00MPUK10.";
      }
      enum "CR5D00MPUK70" {
        description
          "CR5D00MPUK70.";
      }
      enum "CR2D00MPUE10" {
        description
          "CR2D00MPUE10.";
      }
      enum "TNRD00MPUK70" {
        description
          "TNRD00MPUK70.";
      }
      enum "CR5D0NPU5070" {
        description
          "CR5D0NPU5070.";
      }
      enum "CX6D0NSU5010" {
        description
          "CX6D0NSU5010.";
      }
      enum "CR2D0NSP5010" {
        description
          "CR2D0NSP5010.";
      }
      enum "CR5DNPU50E70" {
        description
          "CR5DNPU50E70.";
      }
      enum "CR2DNSPE5010" {
        description
          "CR2DNSPE5010.";
      }
      enum "CX6DNPUI120" {
        description
          "CR5D0NPU120.";
      }
      enum "CX6DNSU12010" {
        description
          "CX6DNSU12010.";
      }
      enum "CR5DNPU12070" {
        description
          "CR5DNPU12070.";
      }
      enum "CR2DNSP12010" {
        description
          "CR2DNSP12010.";
      }
      enum "CR5DNPU1207E" {
        description
          "CR5DNPU1207E.";
      }
      enum "CR2DNSP1201E" {
        description
          "CR2DNSP1201E.";
      }
      enum "CX6X0PWRDC70" {
        description
          "CX6X0PWRDC70.";
      }
      enum "CX6M001FBX71" {
        description
          "CX6M001FBX71.";
      }
      enum "CX6M002FBX72" {
        description
          "CX6M002FBX72.";
      }
      enum "CX6M002FBX73" {
        description
          "CX6M002FBX73.";
      }
      enum "fname8090CX600-M8-AC" {
        description
          "CX600-M8-AC chassis.";
      }
      enum "fname8090CX600-M4" {
        description
          "CX600-M4 chassis.";
      }
      enum "fname8090CX600-M16" {
        description
          "CX600-M16 chassis.";
      }
      enum "fname8090CX600-X2-M8-AC" {
        description
          "CX600-X2-M8-AC chassis.";
      }
      enum "fname8090CX600-X1" {
        description
          "CX600-X1 chassis.";
      }
      enum "fname8090CX600-X2" {
        description
          "CX600-X2 chassis.";
      }
      enum "fname8090CX600-X1-M4" {
        description
          "CX600-X1-M4 chassis.";
      }
      enum "fname8090CX600-X2-M16" {
        description
          "CX600-X2-M16 chassis.";
      }
      enum "fname8090NE20E-X1" {
        description
          "NE20E-X1 chassis.";
      }
      enum "fname8090NE20E-X1-M4" {
        description
          "NE20E-X1-M4 chassis.";
      }
      enum "fname8090NE20E-X2" {
        description
          "NE20E-X2 chassis.";
      }
      enum "fname8090NE20E-X2-M8" {
        description
          "NE20E-X2-M8 chassis.";
      }
      enum "fname8031CX600-M2E" {
        description
          "CX600-M2E chassis.";
      }
      enum "fname8031CX600-M2F" {
        description
          "CX600-M2F chassis.";
      }
      enum "fname8090NE20E-X2-M16" {
        description
          "NE20E-X2-M16 chassis.";
      }
      enum "fnameNE20E-S2E" {
        description
          "NE20E-S2E chassis.";
      }
      enum "fnameNE20E-S2F" {
        description
          "NE20E-S2F chassis.";
      }
      enum "fname8090NE40E-X1" {
        description
          "NE40E-X1 chassis.";
      }
      enum "fname8090NE40E-X1-M4" {
        description
          "NE40E-X1-M4 chassis.";
      }
      enum "fname8090NE40E-X2" {
        description
          "NE40E-X2 chassis.";
      }
      enum "fname8090NE40E-M2E" {
        description
          "NE40E-M2E chassis.";
      }
      enum "fname8090NE40E-M2F" {
        description
          "NE40E-M2F chassis.";
      }
      enum "fname8090NE40E-X8" {
        description
          "NE40E-X8 chassis.";
      }
      enum "fname8090NE40E-X16" {
        description
          "NE40E-X16 chassis.";
      }
      enum "fname8090NE40E-X16A" {
        description
          "NE40E-X16A chassis.";
      }
      enum "fname8090NE40E-X16A-HVDC" {
        description
          "NE40E-X16A-HVDC chassis.";
      }
      enum "fname8090NE40E-X8A-HVDC" {
        description
          "NE40E-X8A-HVDC chassis.";
      }
      enum "fnameME60-X16A-HVDC" {
        description
          "ME60-X16A-HVDC chassis.";
      }
      enum "fnameME60-X8A-HVDC" {
        description
          "ME60-X8A-HVDC chassis.";
      }
      enum "fname8090CX600-X16A-HVDC" {
        description
          "CX600-X16A-HVDC chassis.";
      }
      enum "fname8090CX600-X8A-HVDC" {
        description
          "CX600-X8A-HVDC chassis.";
      }
      enum "fnamePTN6900-16A-HVDC" {
        description
          "PTN 6900-16A-HVDC chassis.";
      }
      enum "fnamePTN6900-8A-HVDC" {
        description
          "PTN 6900-8A-HVDC chassis.";
      }
      enum "fname8090CX600-X16A-DO-HVDC" {
        description
          "CX600-X16A-DO-HVDC chassis.";
      }
      enum "fname8090CX600-X8A-DO-HVDC" {
        description
          "CX600-X8A-DO-HVDC chassis.";
      }
      enum "fname8090NE40E-X16A-AC" {
        description
          "NE40E-X16A-AC chassis.";
      }
      enum "fname8090NE40E-X8A-AC" {
        description
          "NE40E-X8A-AC chassis.";
      }
      enum "fnameME60-X16A-AC" {
        description
          "ME60-X16A-AC chassis.";
      }
      enum "fnameME60-X8A-AC" {
        description
          "ME60-X8A-AC chassis.";
      }
      enum "fname8090CX600-X16A-AC" {
        description
          "CX600-X16A-AC chassis.";
      }
      enum "fname8090CX600-X8A-AC" {
        description
          "CX600-X8A-AC chassis.";
      }
      enum "fnamePTN6900-16A-AC" {
        description
          "PTN 6900-16A-AC chassis.";
      }
      enum "fnamePTN6900-8A-AC" {
        description
          "PTN 6900-8A-AC chassis.";
      }
      enum "fname8090CX600-X16A-DO-AC" {
        description
          "CX600-X16A-DO-AC chassis.";
      }
      enum "fname8090CX600-X8A-DO-AC" {
        description
          "CX600-X8A-DO-AC chassis.";
      }
      enum "fname8090NE40E-X16A-DC" {
        description
          "NE40E-X16A-DC chassis.";
      }
      enum "fname8090NE40E-X8A" {
        description
          "NE40E-X8A chassis.";
      }
      enum "fname8090NE40E-X8A-DC" {
        description
          "NE40E-X8A-DC chassis.";
      }
      enum "fname8090NE40E-X2-M8-AC" {
        description
          "NE40E-X2-M8-AC chassis.";
      }
      enum "fname8090NE40E-X2-M16" {
        description
          "NE40E-X2-M16 chassis.";
      }
      enum "fname8090NE20E-S4" {
        description
          "NE20E-S4 chassis.";
      }
      enum "fname8090NE20E-S8-AC" {
        description
          "NE20E-S8-AC chassis.";
      }
      enum "fname8090NE20E-S16" {
        description
          "NE20E-S16 chassis.";
      }
      enum "fname8090PTN6900-1-M4" {
        description
          "PTN 6900-1-M4 Chassis.";
      }
      enum "fname8090PTN6900-2-M8-AC" {
        description
          "PTN 6900-2-M8-AC Chassis.";
      }
      enum "fname8090PTN6900-2-M16" {
        description
          "PTN 6900-2-M16 Chassis.";
      }
      enum "fnamePTN6900-M2E" {
        description
          "PTN 6900-M2E chassis.";
      }
      enum "fnamePTN6900-M2F" {
        description
          "PTN 6900-M2F chassis.";
      }
      enum "fname8090NE40E-M2H" {
        description
          "NE40E-M2H chassis.";
      }
      enum "fname8031CX600-M2H" {
        description
          "CX600-M2H chassis.";
      }
      enum "CX6D00E8GE10" {
        description
          "CX6D00E8GE10.";
      }
      enum "CR5D00E8GE70" {
        description
          "CR5D00E8GE70.";
      }
      enum "CR2D00E8GE11" {
        description
          "CR2D00E8GE11.";
      }
      enum "CX6D00L2XF10" {
        description
          "CX6D00L2XF10.";
      }
      enum "CR5D00L2XF70" {
        description
          "CR5D00L2XF70.";
      }
      enum "CR2D00L2XF11" {
        description
          "CR2D00L2XF11.";
      }
      enum "CX6D00E8GF10" {
        description
          "CX6D00E8GF10.";
      }
      enum "CR5D00E8GF71" {
        description
          "CR5D00E8GF71.";
      }
      enum "CR2D00E8GF11" {
        description
          "CR2D00E8GF11.";
      }
      enum "CX6D000IE170" {
        description
          "CX6D000IE170.";
      }
      enum "CX6D000IE171" {
        description
          "CX6D000IE171.";
      }
      enum "CR56LPUF400A" {
        description
          "CR56LPUF400A.";
      }
      enum "CR56MPUB5" {
        description
          "CR56MPUB5.";
      }
      enum "CR5DLPUFK061" {
        description
          "CR5DLPUFK061.";
      }
      enum "CR5D00LMXF61" {
        description
          "CR5D00LMXF61.";
      }
      enum "CR5D00LAXF60" {
        description
          "CR5D00LAXF60.";
      }
      enum "CR5D0MPUB560" {
        description
          "CR5D0MPUB560.";
      }
      enum "CR5D0MPUC061" {
        description
          "CR5D0MPUC061.";
      }
      enum "CR2D00P4CF11" {
        description
          "CR2D00P4CF11.";
      }
      enum "CX6D00L4XF10" {
        description
          "CX6D00L4XF10.";
      }
      enum "CR5D00L4XF70" {
        description
          "CR5D00L4XF70.";
      }
      enum "CR2D00L4XF10" {
        description
          "CR2D00L4XF10.";
      }
      enum "CX6DL1XE8G10" {
        description
          "CX6DL1XE8G10.";
      }
      enum "CR5DL1XE8G70" {
        description
          "CR5DL1XE8G70.";
      }
      enum "CR2DL1XE8G10" {
        description
          "CR2DL1XE8G10.";
      }
      enum "CR5D00C4CF71" {
        description
          "CR5D00C4CF71.";
      }
      enum "CX6D00C4CF11" {
        description
          "CX6D00C4CF11.";
      }
      enum "CR2D00C4CF11" {
        description
          "CR2D00C4CF11.";
      }
      enum "CR5D000IE170" {
        description
          "CR5D000IE170.";
      }
      enum "CX6D000IE110" {
        description
          "CX6D000IE110.";
      }
      enum "CR2D000IE110" {
        description
          "CR2D000IE110.";
      }
      enum "CR5D000IE171" {
        description
          "CR5D000IE171.";
      }
      enum "CX6D000IE111" {
        description
          "CX6D000IE111.";
      }
      enum "CR2D000IE111" {
        description
          "CR2D000IE111.";
      }
      enum "CR5D000DE170" {
        description
          "CR5D000DE170.";
      }
      enum "CX6D000DE110" {
        description
          "CX6D000DE110.";
      }
      enum "CR2D000DE110" {
        description
          "CR2D000DE110.";
      }
      enum "CR5D000DE171" {
        description
          "CR5D000DE171.";
      }
      enum "CX6D000DE111" {
        description
          "CX6D000DE111.";
      }
      enum "CR2D000DE111" {
        description
          "CR2D000DE111.";
      }
      enum "CR5DSFU0K06B" {
        description
          "CR5DSFU0K06B.";
      }
      enum "CR5D00C4T370" {
        description
          "CR5D00C4T370.";
      }
      enum "CR57EFGFB" {
        description
          "CR57EFGFB";
      }
      enum "CR57EFGFB2" {
        description
          "CR57EFGFB2.";
      }
      enum "CR57LBXF" {
        description
          "CR57LBXF.";
      }
      enum "CR57LBXF2" {
        description
          "CR57LBXF2.";
      }
      enum "CR57E1NCB2" {
        description
          "CR57E1NCB2.";
      }
      enum "CR57E1MCB" {
        description
          "CR57E1MCB.";
      }
      enum "CR57E1MCB2" {
        description
          "CR57E1MCB2.";
      }
      enum "CR57L6XF" {
        description
          "CR57L6XF.";
      }
      enum "CR57L6XF0" {
        description
          "CR57L6XF0.";
      }
      enum "CR57P8UF" {
        description
          "CR57P8UF.";
      }
      enum "CR5D0P8UF70" {
        description
          "CR5D0P8UF70.";
      }
      enum "CR5D00LBXF72" {
        description
          "CR5D00LBXF72.";
      }
      enum "CR5D0L6XFA70" {
        description
          "CR5D0L6XFA70.";
      }
      enum "CR5D00E1NC75" {
        description
          "CR5D00E1NC75.";
      }
      enum "CR5D0EFGFA71" {
        description
          "CR5D0EFGFA71.";
      }
      enum "CR5D00E1MC70" {
        description
          "CR5D00E1MC70.";
      }
      enum "CR5D00P8UF70" {
        description
          "CR5D00P8UF70.";
      }
      enum "CR5D00E1NC74" {
        description
          "CR5D00E1NC74.";
      }
      enum "CR5D00LBXF71" {
        description
          "CR5D00LBXF71.";
      }
      enum "CR57LPUF480B" {
        description
          "CR57LPUF480B.";
      }
      enum "CR57FRA200A" {
        description
          "CR57FRA200A.";
      }
      enum "CR57LPUF120A" {
        description
          "CR57LPUF120A.";
      }
      enum "CR57LPUF240A" {
        description
          "CR57LPUF240A.";
      }
      enum "CR57SRU200A" {
        description
          "CR57SRU200A.";
      }
      enum "CR57SFU200C" {
        description
          "CR57SFU200C.";
      }
      enum "CR57SFU200B" {
        description
          "CR57SFU200B.";
      }
      enum "CR5DLPUFB070" {
        description
          "CR5DLPUFB070.";
      }
      enum "CR5DLPUFB07B" {
        description
          "CR5DLPUFB07B.";
      }
      enum "CR5DLPUFF070" {
        description
          "CR5DLPUFF070.";
      }
      enum "CR5DLPUFF080" {
        description
          "CR5DLPUFF080.";
      }
      enum "CR5DLPUFF07B" {
        description
          "CR5DLPUFF07B.";
      }
      enum "CR5DSFUIE07B" {
        description
          "CR5DSFUIE07B.";
      }
      enum "CR5DSFUIE07D" {
        description
          "CR5DSFUIE07D.";
      }
      enum "CR5D0MPUB570" {
        description
          "CR5D0MPUB570.";
      }
      enum "CX6D0MPUB570" {
        description
          "CX6D0MPUB570.";
      }
      enum "CR5D0SRUA970" {
        description
          "CR5D0SRUA970.";
      }
      enum "CR5D0SRUA870" {
        description
          "CR5D0SRUA870.";
      }
      enum "CX6D0SRUA970" {
        description
          "CX6D0SRUA970.";
      }
      enum "CX6D0SRUA870" {
        description
          "CX6D0SRUA870.";
      }
      enum "CR5D00E8NC70" {
        description
          "CR5D00E8NC70.";
      }
      enum "CR5D00E8NC7B" {
        description
          "CR5D00E8NC7B.";
      }
      enum "CR5DLPUF517E" {
        description
          "CR5DLPUF517E";
      }
      enum "CR5D0EMGFA7J" {
        description
          "CR5D0EMGFA7J.";
      }
      enum "CR5DL2XEFG7J" {
        description
          "CR5DL2XEFG7J.";
      }
      enum "CR5DSFUIU07C" {
        description
          "CR5DSFUIU07C.";
      }
      enum "CR5DSFUIM07C" {
        description
          "CR5DSFUIM07C.";
      }
      enum "CX6DSFUIU07C" {
        description
          "CX6DSFUIU07C.";
      }
      enum "CX6DSFUIM07C" {
        description
          "CX6DSFUIM07C.";
      }
      enum "CR5DSFUIU07B" {
        description
          "CR5DSFUIU07B.";
      }
      enum "CR5DSFUIM07B" {
        description
          "CR5DSFUIM07B.";
      }
      enum "CX6DSFUIU07B" {
        description
          "CX6DSFUIU07B.";
      }
      enum "CX6DSFUIM07B" {
        description
          "CX6DSFUIM07B.";
      }
      enum "CR57FRA1TA" {
        description
          "CR57FRA1TA.";
      }
      enum "CR5D0LBXFA70" {
        description
          "CR5D0LBXFA70.";
      }
      enum "CR5D0E2MCA70" {
        description
          "CR5D0E2MCA70.";
      }
      enum "CR5D00E1NC76" {
        description
          "CR5D00E1NC76.";
      }
      enum "CR5D00E1NC78" {
        description
          "CR5D00E1NC78.";
      }
      enum "CR5D0LBXFA7B" {
        description
          "CR5D0LBXFA7B.";
      }
      enum "CR5D0E2MCA7B" {
        description
          "CR5D0E2MCA7B.";
      }
      enum "CR5D00E1NC7B" {
        description
          "CR5D00E1NC7B.";
      }
      enum "CR5D00E1NC7C" {
        description
          "CR5D00E1NC7C.";
      }
      enum "CR5D00E2NC70" {
        description
          "CR5D00E2NC70.";
      }
      enum "CR5D00E2NC71" {
        description
          "CR5D00E2NC71.";
      }
      enum "CR5D00LFXF70" {
        description
          "CR5D00LFXF70.";
      }
      enum "CR5DE2NLBX70" {
        description
          "CR5DE2NLBX70.";
      }
      enum "CR5DE1NLBX70" {
        description
          "CR5DE1NLBX70.";
      }
      enum "CR5D00E2NC73" {
        description
          "CR5D00E2NC73.";
      }
      enum "CR5D00E2NC74" {
        description
          "CR5D00E2NC74.";
      }
      enum "CR5D00LFXF73" {
        description
          "CR5D00LFXF73.";
      }
      enum "CR5DE2NLBX73" {
        description
          "CR5DE2NLBX73.";
      }
      enum "CR5DE1NLBX71" {
        description
          "CR5DE1NLBX71.";
      }
      enum "CR5DSFUIE07C" {
        description
          "CR5DSFUIE07C.";
      }
      enum "CX6DSFUIE01C" {
        description
          "CX6DSFUIE01C.";
      }
      enum "CR5D0SRUA570" {
        description
          "CR5D0SRUA570.";
      }
      enum "CX6D0SRUA510" {
        description
          "CX6D0SRUA510.";
      }
      enum "CX6DSFUIE01B" {
        description
          "CX6DSFUIE01B.";
      }
      enum "CR5D0MPUB460" {
        description
          "CR5D0MPUB460.";
      }
      enum "CX6D0MPUB410" {
        description
          "CX6D0MPUB410.";
      }
      enum "CR5DLPUFM070" {
        description
          "CR5DLPUFM070.";
      }
      enum "CR5D00LMXF70" {
        description
          "CR5D00LMXF70.";
      }
      enum "CR5DE2NLFX70" {
        description
          "CR5DE2NLFX70.";
      }
      enum "CR5D00E4NC70" {
        description
          "CR5D00E4NC70.";
      }
      enum "CR5D00D4NC70" {
        description
          "CR5D00D4NC70.";
      }
      enum "CR5D00D8NC70" {
        description
          "CR5D00D8NC70.";
      }
      enum "CR5DLPUFME70" {
        description
          "CR5DLPUFME70.";
      }
      enum "ME0DBSUFM070" {
        description
          "ME0DBSUFM070.";
      }
      enum "ME0DMSUFM070" {
        description
          "ME0DMSUFM070.";
      }
      enum "fname8090CX600-X8" {
        description
          "CX600-X8 chassis.";
      }
      enum "fname8090CX600-X8A" {
        description
          "CX600-X8A chassis.";
      }
      enum "fname8090CX600-X8A-DC" {
        description
          "CX600-X8A-DC chassis.";
      }
      enum "fname8090CX600-X16" {
        description
          "CX600-X16 chassis.";
      }
      enum "fname8090CX600-X16A" {
        description
          "CX600-X16A chassis.";
      }
      enum "fname8090CX600-X16A-DC" {
        description
          "CX600-X16A-DC chassis.";
      }
      enum "fnamePTN6900TNRK003BKP01" {
        description
          "PTN 6900-3 chassis.";
      }
      enum "fnamePTN6900TNRZ1BKPE" {
        description
          "PTN 6900-3-DC chassis.";
      }
      enum "fname8031CX6003AC" {
        description
          "CX600-X3 chassis.";
      }
      enum "fname8031CX6003DCDO" {
        description
          "CX600-X3-DC-DO chassis.";
      }
      enum "fname8031CX6003ACDO" {
        description
          "CX600-X3-AC-DO chassis.";
      }
      enum "fname8031CX600X8DO" {
        description
          "CX600-X8-DO chassis.";
      }
      enum "fname8031CX6003DC" {
        description
          "CX600-X3-DC chassis.";
      }
      enum "fname8090NE40E3AC" {
        description
          "NE40E-X3 chassis.";
      }
      enum "fname8090NE40E3DC" {
        description
          "NE40E-X3-DC chassis.";
      }
      enum "fnameME60-X3-AC" {
        description
          "ME60-X3 chassis.";
      }
      enum "fnameME60-X3-DC" {
        description
          "ME60-X3-DC chassis.";
      }
      enum "fnamePTN6900-3A" {
        description
          "PTN 6900-3A chassis.";
      }
      enum "fnameME60-X3A" {
        description
          "ME60-X3A chassis.";
      }
      enum "fname8090NE40E-X3A" {
        description
          "NE40E-X3A chassis.";
      }
      enum "fname8031CX600-X3A" {
        description
          "CX600-X3A chassis.";
      }
      enum "fnameME60-X8" {
        description
          "ME60-X8 chassis.";
      }
      enum "fnameME60-X16" {
        description
          "ME60-X16 chassis.";
      }
      enum "fnameME60-X8A" {
        description
          "ME60-X8A chassis.";
      }
      enum "fnameME60-X8A-DC" {
        description
          "ME60-X8A-DC chassis.";
      }
      enum "fnameME60-X16A" {
        description
          "ME60-X16A chassis.";
      }
      enum "fnameME60-X16A-DC" {
        description
          "ME60-X16A-DC chassis.";
      }
      enum "fnamePTN6900Half" {
        description
          "PTN 6900-8 chassis.";
      }
      enum "fnamePTN6900Whole" {
        description
          "PTN 6900-16 chassis.";
      }
      enum "fnamePTN6900-8A" {
        description
          "PTN 6900-8A chassis.";
      }
      enum "fnamePTN6900-8A-DC" {
        description
          "PTN 6900-8A-DC chassis.";
      }
      enum "fnamePTN6900-16A" {
        description
          "PTN 6900-16A chassis.";
      }
      enum "fnamePTN6900-16A-DC" {
        description
          "PTN 6900-16A-DC chassis.";
      }
      enum "fname8090CX600-X8A-DO" {
        description
          "CX600-X8A-DO chassis.";
      }
      enum "fname8090CX600-X8A-DO-DC" {
        description
          "CX600-X8A-DO-DC chassis.";
      }
      enum "fname8090CX600-X16A-DO" {
        description
          "CX600-X16A-DO chassis.";
      }
      enum "fname8090CX600-X16A-DO-DC" {
        description
          "CX600-X16A-DO-DC chassis.";
      }
      enum "fname8090CX600-X16-DO" {
        description
          "CX600-X16-DO chassis.";
      }
      enum "fname8031CX600-X3A-DO" {
        description
          "CX600-X3A-DO chassis.";
      }
      enum "fname8090CX600-X2-M8A-AC" {
        description
          "CX600-X2-M8A-AC chassis.";
      }
      enum "fname8090CX600-X2-M8A-DC" {
        description
          "CX600-X2-M8A-DC chassis.";
      }
      enum "fname8031CX600-M8ADO" {
        description
          "CX600-M8ADO chassis.";
      }
      enum "fname8031CX600-M8ADO-DC" {
        description
          "CX600-M8ADO-DC chassis.";
      }
      enum "fname8090NE20E-S8A-AC" {
        description
          "NE20E-S8A-AC chassis.";
      }
      enum "fname8090NE20E-S8A-DC" {
        description
          "NE20E-S8A-DC chassis.";
      }
      enum "fname8090NE40E-X2-M8A-AC" {
        description
          "NE40E-X2-M8A-AC chassis.";
      }
      enum "fname8090NE40E-X2-M8A-DC" {
        description
          "NE40E-X2-M8A-DC chassis.";
      }
      enum "fname8090PTN6900-2-M8A-AC" {
        description
          "PTN 6900-2-M8A-AC chassis.";
      }
      enum "fname8090PTN6900-2-M8A-DC" {
        description
          "PTN 6900-2-M8A-DC chassis.";
      }
      enum "fnameME60-X2-M8A-AC" {
        description
          "ME60-X2-M8A-AC chassis.";
      }
      enum "fnameME60-X2-M8A-DC" {
        description
          "ME60-X2-M8A-DC chassis.";
      }
      enum "fname8090CX600-X2-M16A" {
        description
          "CX600-X2-M16A chassis.";
      }
      enum "fname8031CX600-M16ADO" {
        description
          "CX600-M16ADO chassis.";
      }
      enum "fname8090NE20E-S16A" {
        description
          "NE20E-S16A chassis.";
      }
      enum "fname8090NE40E-X2-M16A" {
        description
          "NE40E-X2-M16A chassis.";
      }
      enum "fname8090PTN6900-2-M16A" {
        description
          "PTN 6900-2-M16A chassis.";
      }
      enum "fnameME60-X2-M16A" {
        description
          "ME60-X2-M16A chassis.";
      }
      enum "fname8090CX600-M8-DC" {
        description
          "CX600-M8-DC chassis.";
      }
      enum "fname8090CX600-X2-M8-DC" {
        description
          "CX600-X2-M8-DC chassis.";
      }
      enum "fname8090NE40E-X2-M8-DC" {
        description
          "NE40E-X2-M8-DC chassis.";
      }
      enum "fname8090NE20E-S8-DC" {
        description
          "NE20E-S8-DC chassis.";
      }
      enum "fname8090PTN6900-2-M8-DC" {
        description
          "PTN 6900-2-M8-DC Chassis.";
      }
      enum "fnameME60-X2-M8-AC" {
        description
          "ME60-X2-M8-AC chassis.";
      }
      enum "fnameME60-X2-M8-DC" {
        description
          "ME60-X2-M8-DC chassis.";
      }
      enum "fnameME60-X2-M16" {
        description
          "ME60-X2-M16 chassis.";
      }
      enum "CR5DSFUIT060" {
        description
          "CR5DSFUIT060.";
      }
      enum "CR5DSFUIT06E" {
        description
          "CR5DSFUIT06E.";
      }
      enum "CR5DSFUIT26A" {
        description
          "CR5DSFUIT26A.";
      }
      enum "CR5DE8NEDX61" {
        description
          "CR5DE8NEDX61";
      }
      enum "CR5D00E8NC61" {
        description
          "CR5D00E8NC61.";
      }
      enum "CR5D00EDNB60" {
        description
          "CR5D00EDNB60.";
      }
      enum "CR5DEDNLIX60" {
        description
          "CR5DEDNLIX60.";
      }
      enum "CR5DLPUFT060" {
        description
          "CR5DLPUFT060.";
      }
      enum "CR56SFU1TA" {
        description
          "CR56SFU1TA.";
      }
      enum "CR5D00EFMB60" {
        description
          "CR5D00EFMB60.";
      }
      enum "CR5D00E8NC60" {
        description
          "CR5D00E8NC60.";
      }
      enum "CR56LPU1TB" {
        description
          "CR56LPU1TB.";
      }
      enum "CR56E8NC" {
        description
          "CR56E8NC.";
      }
      enum "CR56EFMB" {
        description
          "CR56EFMB.";
      }
      enum "CR50OFC400C" {
        description
          "CR50OFC400C.";
      }
      enum "fname8090NE5000E-X8" {
        description
          "NE5000EX8 Chassis.";
      }
      enum "fname8090NE9000-20" {
        description
          "NE9000-20 Chassis.";
      }
      enum "CR5D0SRUB060" {
        description
          "CR5D0SRUB060.";
      }
      enum "CR56SRUB1TA" {
        description
          "CR56SRUB1TA.";
      }
      enum "CR5D0SFUT061" {
        description
          "CR5D0SFUT061.";
      }
      enum "CR56SFU1TC" {
        description
          "CR56SFU1TC.";
      }
      enum "CR56FRA1TA" {
        description
          "CR56FRA1TA.";
      }
      enum "CR5D00LFXF74" {
        description
          "CR5D00LFXF74.";
      }
      enum "CR5D00E2NC72" {
        description
          "CR5D00E2NC72.";
      }
      enum "CR57LFXFE1" {
        description
          "CR57LFXFE1.";
      }
      enum "CR57E2NCE1" {
        description
          "CR57E2NCE1.";
      }
      enum "CR57L2XFB" {
        description
          "CR57L2XFB.";
      }
      enum "CR5D0L2XFA71" {
        description
          "CR5D0L2XFA71.";
      }
      enum "CR5D0EFGFA70" {
        description
          "CR5D0EFGFA70.";
      }
      enum "CR5D00N2NC61" {
        description
          "CR5D00N2NC61.";
      }
      enum "CR5D00E1NC62" {
        description
          "CR5D00E1NC62.";
      }
      enum "CR57L2XFC2" {
        description
          "CR57L2XFC2.";
      }
      enum "CR5DNPU24070" {
        description
          "CR5DNPU24070.";
      }
      enum "CR5DNPU24071" {
        description
          "CR5DNPU24071.";
      }
      enum "CR2DNSPA0010" {
        description
          "CR2DNSPA0010.";
      }
      enum "CR2DNSPB0010" {
        description
          "CR2DNSPB0010.";
      }
      enum "CR5DNPU48070" {
        description
          "CR5DNPU48070.";
      }
      enum "CR2DNSPC0010" {
        description
          "CR2DNSPC0010.";
      }
      enum "CX6D0MPUK170" {
        description
          "CX6D0MPUK170.";
      }
      enum "ME0D0MPUK171" {
        description
          "ME0D0MPUK171.";
      }
      enum "CR5D0MPUK170" {
        description
          "CR5D0MPUK170.";
      }
      enum "TNUD00MPUK71" {
        description
          "TNUD00MPUK71.";
      }
      enum "CR2D0MPUE110" {
        description
          "CR2D0MPUE110.";
      }
      enum "CR2DP4C2HF11" {
        description
          "CR2DP4C2HF11.";
      }
      enum "CR5DP4C2HF70" {
        description
          "CR5DP4C2HF70.";
      }
      enum "CR2DP2C1HF11" {
        description
          "CR2DP2C1HF11.";
      }
      enum "CR5DP2C1HF70" {
        description
          "CR5DP2C1HF70.";
      }
      enum "CR5DLPUF5070" {
        description
          "CR5DLPUF5070.";
      }
      enum "CR5DLPUF5170" {
        description
          "CR5DLPUF5170.";
      }
      enum "CR5DLPUF517B" {
        description
          "CR5DLPUF517B.";
      }
      enum "CR5D0L5XFA71" {
        description
          "CR5D0L5XFA71.";
      }
      enum "CR5D0L4XFA70" {
        description
          "CR5D0L4XFA70.";
      }
      enum "CR5D0EMGFA70" {
        description
          "CR5D0EMGFA70.";
      }
      enum "CR5DL2XEFG7A" {
        description
          "CR5DL2XEFG7A.";
      }
      enum "CR5DL3XEFG7C" {
        description
          "CR5DL3XEFG7C.";
      }
      enum "CR5D0L5XFA7B" {
        description
          "CR5D0L5XFA7B.";
      }
      enum "CR5D0L4XFA7B" {
        description
          "CR5D0L4XFA7B.";
      }
      enum "CR5D0EMGFA7B" {
        description
          "CR5D0EMGFA7B.";
      }
      enum "CR5DL2XEFG7B" {
        description
          "CR5DL2XEFG7B.";
      }
      enum "CR5D00L5XF72" {
        description
          "CR5D00L5XF72.";
      }
      enum "CR5D00EMGF73" {
        description
          "CR5D00EMGF73.";
      }
      enum "CR5DL2XEFG72" {
        description
          "CR5DL2XEFG72.";
      }
      enum "CR5D0L5XFA7L" {
        description
          "CR5D0L5XFA7L.";
      }
      enum "CR5DL2XEIG7L" {
        description
          "CR5DL2XEIG7L.";
      }
      enum "CR5D0EMGFA7L" {
        description
          "CR5D0EMGFA7L.";
      }
      enum "CR5DLPUFA071" {
        description
          "CR5DLPUFA071.";
      }
      enum "CR5DLPUFA07B" {
        description
          "CR5DLPUFA07B.";
      }
      enum "CR5D00E2MC70" {
        description
          "CR5D00E2MC70.";
      }
      enum "CR5D0LAXFA71" {
        description
          "CR5D0LAXFA71.";
      }
      enum "CR5D00E1NC72" {
        description
          "CR5D00E1NC72.";
      }
      enum "CR5D00E2MC7B" {
        description
          "CR5D00E2MC7B.";
      }
      enum "CR5D0LAXFA7B" {
        description
          "CR5D0LAXFA7B.";
      }
      enum "CR5D00E2MC71" {
        description
          "CR5D00E2MC71.";
      }
      enum "CR5D0LAXFA72" {
        description
          "CR5D0LAXFA72.";
      }
      enum "CR5D00E1NC73" {
        description
          "CR5D00E1NC73.";
      }
      enum "ME0DBSUFA070" {
        description
          "ME0DBSUFA070.";
      }
      enum "ME0DBSUFF070" {
        description
          "ME0DBSUFF070.";
      }
      enum "CR5DLPUFB07E" {
        description
          "CR5DLPUFB07E.";
      }
      enum "CR5DLPUFF07E" {
        description
          "CR5DLPUFF07E.";
      }
      enum "ME0DMSUFA070" {
        description
          "ME0DMSUFA070.";
      }
      enum "ME0DMSUF5170" {
        description
          "ME0DMSUF5170.";
      }
      enum "ME0DBSUF5170" {
        description
          "ME0DBSUF5170.";
      }
      enum "CR5DLPUF507L" {
        description
          "CR5DLPUF507L.";
      }
      enum "CR5DL4XEBG7L" {
        description
          "CR5DL4XEBG7L.";
      }
      enum "CR5D0L5XFA7J" {
        description
          "CR5D0L5XFA7J.";
      }
      enum "CR5D00LBXF7L" {
        description
          "CR5D00LBXF7L.";
      }
      enum "CR5D00L5XF73" {
        description
          "CR5D00L5XF73.";
      }
      enum "CR5D00EMGF74" {
        description
          "CR5D00EMGF74.";
      }
      enum "CR5DL2XEFG73" {
        description
          "CR5DL2XEFG73.";
      }
      enum "CR5DLPUFA07J" {
        description
          "CR5DLPUFA07J.";
      }
      enum "CR5DLPUFA27E" {
        description
          "CR5DLPUFA27E.";
      }
      enum "CR5D00LFXF7L" {
        description
          "CR5D00LFXF7L.";
      }
      enum "CR5D00TBXF71" {
        description
          "CR5D00TBXF71.";
      }
      enum "CR5D00TFXF71" {
        description
          "CR5D00TFXF71.";
      }
      enum "CR5D0MPUD170" {
        description
          "CR5D0MPUD170.";
      }
      enum "CR5D0MPUD270" {
        description
          "CR5D0MPUD270.";
      }
      enum "CX6D0MPUD170" {
        description
          "CX6D0MPUD170.";
      }
      enum "CX6D0MPUD270" {
        description
          "CX6D0MPUD270.";
      }
      enum "TNRD0MPUD270" {
        description
          "TNRD0MPUD270.";
      }
      enum "TNRD0MPUD370" {
        description
          "TNRD0MPUD370.";
      }
      enum "ME0D00MPUD71" {
        description
          "ME0D00MPUD71.";
      }
      enum "ME0D00MPUD72" {
        description
          "ME0D00MPUD72.";
      }
      enum "CR5D0MPUD470" {
        description
          "CR5D0MPUD470.";
      }
      enum "CX6D0MPUD470" {
        description
          "CX6D0MPUD470.";
      }
      enum "TNRD0MPUD470" {
        description
          "TNRD0MPUD470.";
      }
      enum "ME0P0MPUD470" {
        description
          "ME0P0MPUD470.";
      }
      enum "CR5D00D2NT70" {
        description
          "CR5D00D2NT70.";
      }
      enum "CR5DLPUFE070" {
        description
          "CR5DLPUFE070.";
      }
      enum "TNRD0SRUA870" {
        description
          "TNRD0SRUA870.";
      }
      enum "TNRDSFUIM07C" {
        description
          "TNRDSFUIM07C.";
      }
      enum "TNRD0SRUA970" {
        description
          "TNRD0SRUA970.";
      }
      enum "TNRDSFUIU07C" {
        description
          "TNRDSFUIU07C.";
      }
      enum "ME0D0SRUA870" {
        description
          "ME0D0SRUA870.";
      }
      enum "ME0D0SRUA970" {
        description
          "ME0D0SRUA970.";
      }
      enum "ME0DSFUIU07C" {
        description
          "ME0DSFUIU07C.";
      }
      enum "ME0DSFUIK07B" {
        description
          "ME0DSFUIK07B.";
      }
      enum "TNRD0MPUB470" {
        description
          "TNRD0MPUB470.";
      }
      enum "TNRD0MPUB570" {
        description
          "TNRD0MPUB570.";
      }
      enum "TNRDSFUIE07B" {
        description
          "TNRDSFUIE07B.";
      }
      enum "ME0D0MPUB570" {
        description
          "ME0D0MPUB570.";
      }
      enum "ME0DSFUIE07B" {
        description
          "ME0DSFUIE07B.";
      }
      enum "TNRD0SRUA570" {
        description
          "TNRD0SRUA570.";
      }
      enum "TNRDSFUIE07C" {
        description
          "TNRDSFUIE07C.";
      }
      enum "TNRDSFUIM07B" {
        description
          "TNRDSFUIM07B.";
      }
      enum "TNRDSFUIU07B" {
        description
          "TNRDSFUIU07B.";
      }
      enum "ME0DSFUIU07B" {
        description
          "ME0DSFUIU07B.";
      }
      enum "ME0DSFUIK07A" {
        description
          "ME0DSFUIK07A.";
      }
      enum "ME0D0MPUB470" {
        description
          "ME0D0MPUB470.";
      }
      enum "ME0DSFUIE07D" {
        description
          "ME0DSFUIE07D.";
      }
      enum "ME0D0SRUA570" {
        description
          "ME0D0SRUA570.";
      }
      enum "ME0DSFUIE07C" {
        description
          "ME0DSFUIE07C.";
      }
      enum "CR5DVSUF8010" {
        description
          "CR5DVSUF8010.";
      }
      enum "ME0DVSUF8070" {
        description
          "ME0DVSUF8070.";
      }
      enum "CR5DVSUFD010" {
        description
          "CR5DVSUFD010.";
      }
      enum "ME0DVSUFD070" {
        description
          "ME0DVSUFD070.";
      }
      enum "CR5D00SP8010" {
        description
          "CR5D00SP8010.";
      }
      enum "CR5D00SPD010" {
        description
          "CR5D00SPD010.";
      }
      enum "ME0D00SP8070" {
        description
          "ME0D00SP8070.";
      }
      enum "ME0D00SPD070" {
        description
          "ME0D00SPD070.";
      }
      enum "CR5DLPUFK062" {
        description
          "CR5DLPUFK062.";
      }
      enum "CR5D00L4NC60" {
        description
          "CR5D00L4NC60.";
      }
      enum "CR5D00LKXF60" {
        description
          "CR5D00LKXF60.";
      }
      enum "CR5DL2NLEX60" {
        description
          "CR5DL2NLEX60.";
      }
      enum "CX6B0BKP0371" {
        description
          "CX6B0BKP0371.";
      }
      enum "CX6B0BKP0372" {
        description
          "CX6B0BKP0372.";
      }
      enum "CR5B0BKP0371" {
        description
          "CR5B0BKP0371.";
      }
      enum "CR5D00L2NC63" {
        description
          "CR5D00L2NC63.";
      }
      enum "CR5D00LEXF63" {
        description
          "CR5D00LEXF63.";
      }
      enum "CR5B0BKP0372" {
        description
          "CR5B0BKP0372.";
      }
      enum "CR2B0BKP0210" {
        description
          "CR2B0BKP0210.";
      }
      enum "CR2B0BKP0211" {
        description
          "CR2B0BKP0211.";
      }
      enum "TNRB0BKP0371" {
        description
          "TNRB0BKP0371.";
      }
      enum "TNRB0BKP0372" {
        description
          "TNRB0BKP0372.";
      }
      enum "CX6D0E8GFA10" {
        description
          "CX6D0E8GFA10.";
      }
      enum "CX6D00CFE110" {
        description
          "CX6D00CFE110.";
      }
      enum "CX6D00C2CF10" {
        description
          "CX6D00C2CF10.";
      }
      enum "CX6D0L5XFA10" {
        description
          "CX6D0L5XFA10.";
      }
      enum "CX6D0L2XFA11" {
        description
          "CX6D0L2XFA11.";
      }
      enum "CX6D0EFGFA10" {
        description
          "CX6D0EFGFA10.";
      }
      enum "CX6D0EEGEA10" {
        description
          "CX6D0EEGEA10.";
      }
      enum "CX6DL1XESG1A" {
        description
          "CX6DL1XESG1A.";
      }
      enum "CX6DL2XEAG1A" {
        description
          "CX6DL2XEAG1A.";
      }
      enum "CX6D0L5XFA12" {
        description
          "CX6D0L5XFA12.";
      }
      enum "CX6D0EFGFA11" {
        description
          "CX6D0EFGFA11.";
      }
      enum "CX6D0E1NCA10" {
        description
          "CX6D0E1NCA10.";
      }
      enum "CX6D0E1MCA10" {
        description
          "CX6D0E1MCA10.";
      }
      enum "CX6D0L5XFH10" {
        description
          "CX6D0L5XFH10.";
      }
      enum "CX6D0L6XFA10" {
        description
          "CX6D0L6XFA10.";
      }
      enum "CX6D0LBXFA10" {
        description
          "CX6D0LBXFA10.";
      }
      enum "CX6D0LAXFA12" {
        description
          "CX6D0LAXFA12.";
      }
      enum "CX6D0E3MFA10" {
        description
          "CX6D0E3MFA10.";
      }
      enum "CX6D0LAXFH10" {
        description
          "CX6D0LAXFH10.";
      }
      enum "CX6D0LBXFA12" {
        description
          "CX6D0LBXFA12.";
      }
      enum "CR5D0EFGFE70" {
        description
          "CR5D0EFGFE70.";
      }
      enum "CR5D0L5XFE70" {
        description
          "CR5D0L5XFE70.";
      }
      enum "CR5D0L2XFE70" {
        description
          "CR5D0L2XFE70.";
      }
      enum "CR5D0L2XFH70" {
        description
          "CR5D0L2XFH70.";
      }
      enum "CR5D0L5XFE71" {
        description
          "CR5D0L5XFE71.";
      }
      enum "CR5D0L5XFH70" {
        description
          "CR5D0L5XFH70.";
      }
      enum "CR5D0E3MFA70" {
        description
          "CR5D0E3MFA70.";
      }
      enum "CR5D0LAXFH70" {
        description
          "CR5D0LAXFH70.";
      }
      enum "CR57EFGFE2" {
        description
          "CR57EFGFE2.";
      }
      enum "CR57L2XFE2" {
        description
          "CR57L2XFE2.";
      }
      enum "CR57LEXFE01" {
        description
          "CR57LEXFE01.";
      }
      enum "CR57L3XFA2" {
        description
          "CR57L3XFA2.";
      }
      enum "CR57L5XFE2" {
        description
          "CR57L5XFE2.";
      }
      enum "CR57E3MB2" {
        description
          "CR57E3MB2.";
      }
      enum "CR53P1XX0" {
        description
          "CR53P1XX0.";
      }
      enum "CR53P2UF0" {
        description
          "CR53P2UF0.";
      }
      enum "CR53P4UF0" {
        description
          "CR53P4UF0.";
      }
      enum "CR53P8HF0" {
        description
          "CR53P8HF0.";
      }
      enum "CR5DVSUID010" {
        description
          "CR5DVSUID010.";
      }
      enum "ME0DVSUID070" {
        description
          "ME0DVSUID070.";
      }
      enum "CR58E8NCD" {
        description
          "CR58E8NCD.";
      }
      enum "CR58EFMBD" {
        description
          "CR58EFMBD.";
      }
      enum "CR58EPXFB" {
        description
          "CR58EPXFB.";
      }
      enum "CR56E8NCB" {
        description
          "CR56E8NCB.";
      }
      enum "CR56EFMBB" {
        description
          "CR56EFMBB.";
      }
      enum "ME0DVSUF8072" {
        description
          "ME0DVSUF8072.";
      }
      enum "ME0DVSUF8073" {
        description
          "ME0DVSUF8073.";
      }
      enum "CR5DVSUF8011" {
        description
          "CR5DVSUF8011.";
      }
      enum "CR5D0EMGFA7P" {
        description
          "CR5D0EMGFA7P.";
      }
      enum "CR5D00LBXF7P" {
        description
          "CR5D00LBXF7P.";
      }
      enum "CR5DL6XEFG7P" {
        description
          "CR5DL6XEFG7P.";
      }
      enum "CR5D00LFXF7P" {
        description
          "CR5D00LFXF7P.";
      }
      enum "CR5D00E8NC7P" {
        description
          "CR5D00E8NC7P.";
      }
      enum "CX6D0L5XFA1B" {
        description
          "CX6D0L5XFA1B.";
      }
      enum "CX6D0EMGFA1B" {
        description
          "CX6D0EMGFA1B.";
      }
      enum "CX6DISUFA110" {
        description
          "CX6DISUFA110.";
      }
      enum "CX6DISUFA210" {
        description
          "CX6DISUFA210.";
      }
      enum "CX6DISUFB010" {
        description
          "CX6DISUFB010.";
      }
      enum "CX6D0LAXFA10" {
        description
          "CX6D0LAXFA10.";
      }
      enum "CX6D0LBXFA11" {
        description
          "CX6D0LBXFA11.";
      }
      enum "CR5DLAXFAJ7E" {
        description
          "CR5DLAXFAJ7E.";
      }
      enum "CR5DL2XEFG7E" {
        description
          "CR5DL2XEFG7E.";
      }
      enum "CX6DISUFE012" {
        description
          "CX6DISUFE012.";
      }
      enum "CX6DISUFE011" {
        description
          "CX6DISUFE011.";
      }
      enum "CX6DISUFF010" {
        description
          "CX6DISUFF010.";
      }
      enum "CX6D0LFXFA10" {
        description
          "CX6D0LFXFA10.";
      }
      enum "CX6DISUF5110" {
        description
          "CX6DISUF5110.";
      }
      enum "CX6DISUF511B" {
        description
          "CX6DISUF511B.";
      }
      enum "CX6DSFUIE07C" {
        description
          "CX6DSFUIE07C.";
      }
      enum "CX6DSFUIA07D" {
        description
          "CX6DSFUIA07D.";
      }
      enum "CX6D0SRUA511" {
        description
          "CX6D0SRUA511.";
      }
      enum "CX6D0SRUA770" {
        description
          "CX6D0SRUA770.";
      }
      enum "CX6D0LEXFA10" {
        description
          "CX6D0LEXFA10.";
      }
      enum "CX6DSFUIE07B" {
        description
          "CX6DSFUIE07B.";
      }
      enum "CR5D0SRUA770" {
        description
          "CR5D0SRUA770.";
      }
      enum "CX6D0MPUB411" {
        description
          "CX6D0MPUB411.";
      }
      enum "CR5D0SRUB570" {
        description
          "CR5D0SRUB570.";
      }
      enum "CR5D0SRUB571" {
        description
          "CR5D0SRUB571.";
      }
      enum "CX6D0SRUB510" {
        description
          "CX6D0SRUB510.";
      }
      enum "ME0D0SRUB570" {
        description
          "ME0D0SRUB570.";
      }
      enum "TNRD0SRUB570" {
        description
          "TNRD0SRUB570.";
      }
      enum "CX6DISUFM010" {
        description
          "CX6DISUFM010.";
      }
      enum "CR5DSFUIA07D" {
        description
          "CR5DSFUIA07D.";
      }
      enum "CR5DLPUFM07B" {
        description
          "CR5DLPUFM07B.";
      }
      enum "CR5D00LMXF7B" {
        description
          "CR5D00LMXF7B.";
      }
      enum "CR5DE2NLFX7B" {
        description
          "CR5DE2NLFX7B.";
      }
      enum "CR5D00E4NC7B" {
        description
          "CR5D00E4NC7B.";
      }
      enum "CX6D0LEXFA11" {
        description
          "CX6D0LEXFA11.";
      }
      enum "CR5D00E8NC7C" {
        description
          "CR5D00E8NC7C.";
      }
      enum "CR5D00LMXF7C" {
        description
          "CR5D00LMXF7C.";
      }
      enum "CR5DE2NLFX7C" {
        description
          "CR5DE2NLFX7C.";
      }
      enum "CR5D00E4NC7C" {
        description
          "CR5D00E4NC7C.";
      }
      enum "ME0DL2XEFG7E" {
        description
          "ME0DL2XEFG7E.";
      }
      enum "CR5D0L5XFA7E" {
        description
          "CR5D0L5XFA7E.";
      }
      enum "CR5D0L5XFA7F" {
        description
          "CR5D0L5XFA7F.";
      }
      enum "CR5DLAXFAJ7F" {
        description
          "CR5DLAXFAJ7F.";
      }
      enum "ME0D0L5XXE71" {
        description
          "ME0D0L5XXE71.";
      }
      enum "ME0D0LAXXH71" {
        description
          "ME0D0LAXXH71.";
      }
      enum "CR5DL2XFFG7E" {
        description
          "CR5DL2XFFG7E.";
      }
      enum "ME0DL2XEFG8E" {
        description
          "ME0DL2XEFG8E.";
      }
      enum "CX6DSFUIM01B" {
        description
          "CX6DSFUIM01B.";
      }
      enum "CX6DSFUIM01C" {
        description
          "CX6DSFUIM01C.";
      }
      enum "CX6D0MPUB510" {
        description
          "CX6D0MPUB510.";
      }
      enum "CX6D0SRUA810" {
        description
          "CX6D0SRUA810.";
      }
      enum "CX6D0MPUD410" {
        description
          "CX6D0MPUD410.";
      }
      enum "ME0DSFUIM07B" {
        description
          "ME0DSFUIM07B.";
      }
      enum "ME0DSFUIM07C" {
        description
          "ME0DSFUIM07C.";
      }
      enum "ME0D0SRUA770" {
        description
          "ME0D0SRUA770.";
      }
      enum "ME0DSFUIA07D" {
        description
          "ME0DSFUIA07D.";
      }
      enum "ME0D00MPUK70" {
        description
          "ME0D00MPUK70.";
      }
      enum "ME0DBSU24071" {
        description
          "ME0DBSU24071.";
      }
      enum "CR5D00A2CF70" {
        description
          "CR5D00A2CF70.";
      }
      enum "CR2D00A2CF10" {
        description
          "CR2D00A2CF10.";
      }
      enum "CR57SRU200B" {
        description
          "CR57SRU200B.";
      }
      enum "CR56E8NCE" {
        description
          "CR56E8NCE.";
      }
      enum "CR56E8NLDXA" {
        description
          "CR56E8NLDXA.";
      }
      enum "CR56EDNBV" {
        description
          "CR56EDNBV.";
      }
      enum "CR56EDNLIXV" {
        description
          "CR56EDNLIXV.";
      }
      enum "CR5D0MPUB571" {
        description
          "CR5D0MPUB571.";
      }
      enum "CX6D0MPUB571" {
        description
          "CX6D0MPUB571.";
      }
      enum "TNRD0MPUB571" {
        description
          "TNRD0MPUB571.";
      }
      enum "ME0D0MPUB571" {
        description
          "ME0D0MPUB571.";
      }
      enum "CR5DMPUX8670" {
        description
          "CR5DMPUX8670.";
      }
      enum "CX6DMPUX8670" {
        description
          "CX6DMPUX8670.";
      }
      enum "ME0DMPUX8670" {
        description
          "ME0DMPUX8670.";
      }
      enum "CR5D0MPUD471" {
        description
          "CR5D0MPUD471.";
      }
      enum "CX6D0MPUD471" {
        description
          "CX6D0MPUD471.";
      }
      enum "TNRD0MPUD471" {
        description
          "TNRD0MPUD471.";
      }
      enum "CR5D0SRUA871" {
        description
          "CR5D0SRUA871.";
      }
      enum "CX6D0SRUA871" {
        description
          "CX6D0SRUA871.";
      }
      enum "TNRD0SRUA871" {
        description
          "TNRD0SRUA871.";
      }
      enum "ME0D0SRUA871" {
        description
          "ME0D0SRUA871.";
      }
      enum "CR5D0SRUA971" {
        description
          "CR5D0SRUA971.";
      }
      enum "CX6D0SRUA971" {
        description
          "CX6D0SRUA971.";
      }
      enum "TNRD0SRUA971" {
        description
          "TNRD0SRUA971.";
      }
      enum "ME0D0SRUA971" {
        description
          "ME0D0SRUA971.";
      }
      enum "CR2D0E8GFH10" {
        description
          "CR2D0E8GFH10.";
      }
      enum "CR2D0L2XFH11" {
        description
          "CR2D0L2XFH11.";
      }
      enum "CR5D0L2XFH72" {
        description
          "CR5D0L2XFH72.";
      }
      enum "CR5D0E8GFH70" {
        description
          "CR5D0E8GFH70.";
      }
      enum "ME0D0EAGFE70" {
        description
          "ME0D0EAGFE70.";
      }
      enum "ME0D0L2XFE71" {
        description
          "ME0D0L2XFE71.";
      }
      enum "CR5D0L5XFE74" {
        description
          "CR5D0L5XFE74.";
      }
      enum "CR5D0L2XFE75" {
        description
          "CR5D0L2XFE75.";
      }
      enum "CR5D0L5XFE76" {
        description
          "CR5D0L5XFE76.";
      }
      enum "ME0D0EFGFE7E" {
        description
          "ME0D0EFGFE7E.";
      }
      enum "ME0D0L5XXE7E" {
        description
          "ME0D0L5XXE7E.";
      }
      enum "ME0D0L5XXE8E" {
        description
          "ME0D0L5XXE8E.";
      }
      enum "ME0D0L2XXE7E" {
        description
          "ME0D0L2XXE7E.";
      }
      enum "ME0D0L2XFH7H" {
        description
          "ME0D0L2XFH7H.";
      }
      enum "ME0D0L5XFH7H" {
        description
          "ME0D0L5XFH7H.";
      }
      enum "CR57L5XFI3" {
        description
          "CR57L5XFI3.";
      }
      enum "CR57L2XFI2" {
        description
          "CR57L2XFI2.";
      }
      enum "CR5D00E1NC79" {
        description
          "CR5D00E1NC79.";
      }
      enum "CR5D00LAXF71" {
        description
          "CR5D00LAXF71.";
      }
      enum "CR2D00LAXF10" {
        description
          "CR2D00LAXF10.";
      }
      enum "CR2D00E1NC10" {
        description
          "CR2D00E1NC10.";
      }
      enum "CR5D1DMD1M01" {
        description
          "CR5D1DMD1M01.";
      }
      enum "CR5D1DMD1M02" {
        description
          "CR5D1DMD1M02.";
      }
      enum "CR5D1DMD1M03" {
        description
          "CR5D1DMD1M03.";
      }
      enum "CR5D1DMD1M04" {
        description
          "CR5D1DMD1M04.";
      }
      enum "CR5D1DMD1M05" {
        description
          "CR5D1DMD1M05.";
      }
      enum "CR5D1DMD1M06" {
        description
          "CR5D1DMD1M06.";
      }
      enum "CR5D1DMD1M07" {
        description
          "CR5D1DMD1M07.";
      }
      enum "CR5D1DMD1M08" {
        description
          "CR5D1DMD1M08.";
      }
      enum "CR5D2DMD2M01" {
        description
          "CR5D2DMD2M01.";
      }
      enum "CR5D2DMD2M02" {
        description
          "CR5D2DMD2M02.";
      }
      enum "CR5D2DMD2M03" {
        description
          "CR5D2DMD2M03.";
      }
      enum "CR5D2DMD2M04" {
        description
          "CR5D2DMD2M04.";
      }
      enum "CR5D0E2NCE70" {
        description
          "CR5D0E2NCE70.";
      }
      enum "CR5D0LEXFE70" {
        description
          "CR5D0LEXFE70.";
      }
      enum "ME0M0LEXFB70" {
        description
          "ME0M0LEXFB70.";
      }
      enum "ME0M0E2NCB70" {
        description
          "ME0M0E2NCB70.";
      }
      enum "CR57EFGFH2" {
        description
          "CR57EFGFH2.";
      }
      enum "CR5D0EFGFE71" {
        description
          "CR5D0EFGFE71.";
      }
      enum "CR58E8NBA" {
        description
          "CR58E8NBA.";
      }
      enum "CR58D8NCA" {
        description
          "CR58D8NCA.";
      }
      enum "CX68LGXF0" {
        description
          "CX68LGXF0.";
      }
      enum "CR5D00E8NB60" {
        description
          "CR5D00E8NB60.";
      }
      enum "CR5DE2NLEX60" {
        description
          "CR5DE2NLEX60.";
      }
      enum "CR5D00LFXF60" {
        description
          "CR5D00LFXF60.";
      }
      enum "CR5D00E4NB60" {
        description
          "CR5D00E4NB60.";
      }
      enum "CR56E4NBA1" {
        description
          "CR56E4NBA1.";
      }
      enum "CR5D00N4NC60" {
        description
          "CR5D00N4NC60.";
      }
      enum "CR5D00LMXB60" {
        description
          "CR5D00LMXB60.";
      }
      enum "ME0D0L8NCA70" {
        description
          "ME0D0L8NCA70.";
      }
      enum "ME0D0L4NCB70" {
        description
          "ME0D0L4NCB70.";
      }
      enum "ME0D0L2NCB70" {
        description
          "ME0D0L2NCB70.";
      }
      enum "ME0D0LFXFA70" {
        description
          "ME0D0LFXFA70.";
      }
      enum "ME0D0LMXFA70" {
        description
          "ME0D0LMXFA70.";
      }
      enum "ME0D0E4NCM70" {
        description
          "ME0D0E4NCM70.";
      }
      enum "ME0D0LKXFB70" {
        description
          "ME0D0LKXFB70.";
      }
      enum "ME0DE2NLEX7B" {
        description
          "ME0DE2NLEX7B.";
      }
      enum "ME0DL3XEFG7B" {
        description
          "ME0DL3XEFG7B.";
      }
      enum "ME0D0LEXFB71" {
        description
          "ME0D0LEXFB71.";
      }
      enum "ME0D0LAXFA70" {
        description
          "ME0D0LAXFA70.";
      }
      enum "ME0D0LEXFB70" {
        description
          "ME0D0LEXFB70.";
      }
      enum "ME0D0E2NCB70" {
        description
          "ME0D0E2NCB70.";
      }
      enum "ME0D0EMGFB70" {
        description
          "ME0D0EMGFB70.";
      }
      enum "ME0D0LAXXB70" {
        description
          "ME0D0LAXXB70.";
      }
      enum "ME0D0L5XXB70" {
        description
          "ME0D0L5XXB70.";
      }
      enum "CR5DLPUFE07E" {
        description
          "CR5DLPUFE07E.";
      }
      enum "ME0DBSUFA071" {
        description
          "ME0DBSUFA071.";
      }
      enum "ME0DBSUFF071" {
        description
          "ME0DBSUFF071.";
      }
      enum "ME0DBSUFK070" {
        description
          "ME0DBSUFK070.";
      }
      enum "CR5DLPUFK070" {
        description
          "CR5DLPUFK070.";
      }
      enum "CR9DLPUFK080" {
        description
          "CR9DLPUFK080.";
      }
      enum "CR9D00EDNB8P" {
        description
          "CR9D00EDNB8P.";
      }
      enum "CR9D00E8NC8P" {
        description
          "CR9D00E8NC8P.";
      }
      enum "CR9D00D8NC8P" {
        description
          "CR9D00D8NC8P.";
      }
      enum "CR9D00EPXF8P" {
        description
          "CR9D00EPXF8P.";
      }
      enum "CR5D00LKXF6P" {
        description
          "CR5D00LKXF6P.";
      }
      enum "CR5D00EDNB6P" {
        description
          "CR5D00EDNB6P.";
      }
      enum "CR5D0EFGFH70" {
        description
          "CR5D0EFGFH70.";
      }
      enum "ME0D0EFGFH7H" {
        description
          "ME0D0EFGFH7H.";
      }
      enum "CR5D0L2XFH73" {
        description
          "CR5D0L2XFH73.";
      }
      enum "ME0D0L2XFH8H" {
        description
          "ME0D0L2XFH8H.";
      }
      enum "CR5D0L5XFH72" {
        description
          "CR5D0L5XFH72.";
      }
      enum "ME0D0L5XFH8H" {
        description
          "ME0D0L5XFH8H.";
      }
      enum "CR5D0EAGFE70" {
        description
          "CR5D0EAGFE70.";
      }
      enum "CR5D0L2XFE71" {
        description
          "CR5D0L2XFE71.";
      }
      enum "CR5D00E1NC77" {
        description
          "CR5D00E1NC77.";
      }
      enum "CR5D00E1NC7A" {
        description
          "CR5D00E1NC7A.";
      }
      enum "ME0D0E1NCB70" {
        description
          "ME0D0E1NCB70.";
      }
      enum "ME0D0E1NCB71" {
        description
          "ME0D0E1NCB71.";
      }
      enum "CR57E1NCF2" {
        description
          "CR57E1NCF2.";
      }
      enum "CX6D0E1NCA11" {
        description
          "CX6D0E1NCA11.";
      }
      enum "CR5D00E1ND70" {
        description
          "CR5D00E1ND70.";
      }
      enum "CR5D00E1ND73" {
        description
          "CR5D00E1ND73.";
      }
      enum "ME0D0E1NDB70" {
        description
          "ME0D0E1NDB70.";
      }
      enum "ME0D0E1NDB71" {
        description
          "ME0D0E1NDB71.";
      }
      enum "CX6D0E1NDA10" {
        description
          "CX6D0E1NDA10.";
      }
      enum "CR5D00E2NB60" {
        description
          "CR5D00E2NB60.";
      }
      enum "CR5D00E2NF70" {
        description
          "CR5D00E2NF70.";
      }
      enum "CR5D3DMR4M01" {
        description
          "CR5D3DMR4M01.";
      }
      enum "CR5D3DMR4M02" {
        description
          "CR5D3DMR4M02.";
      }
      enum "CR5D00MD8A70" {
        description
          "CR5D00MD8A70.";
      }
      enum "CR2D0EAGFE10" {
        description
          "CR2D0EAGFE10.";
      }
      enum "CR2D0L2XFE10" {
        description
          "CR2D0L2XFE10.";
      }
      enum "CR5D0E2NCE71" {
        description
          "CR5D0E2NCE71.";
      }
      enum "ME0M0E2NCB71" {
        description
          "ME0M0E2NCB71.";
      }
      enum "CR5D0LEXFE71" {
        description
          "CR5D0LEXFE71.";
      }
      enum "ME0M0LEXFB71" {
        description
          "ME0M0LEXFB71.";
      }
      enum "CR5D0L6XFH70" {
        description
          "CR5D0L6XFH70.";
      }
      enum "ME0D0L6XFH7H" {
        description
          "ME0D0L6XFH7H.";
      }
      enum "CR5D0LBXFH70" {
        description
          "CR5D0LBXFH70.";
      }
      enum "ME0D0LBXFH7H" {
        description
          "ME0D0LBXFH7H.";
      }
      enum "CR5D00N6GF60" {
        description
          "CR5D00N6GF60.";
      }
      enum "CR5D00NBGF60" {
        description
          "CR5D00NBGF60.";
      }
      enum "CR9D00LFXF80" {
        description
          "CR9D00LFXF80.";
      }
      enum "CR9D00NBXF80" {
        description
          "CR9D00NBXF80.";
      }
      enum "CR9D00N6XF80" {
        description
          "CR9D00N6XF80.";
      }
      enum "CR9D00P8UF80" {
        description
          "CR9D00P8UF80.";
      }
      enum "CR9D00P4XX80" {
        description
          "CR9D00P4XX80.";
      }
      enum "CR5D00EEGF71" {
        description
          "CR5D00EEGF71.";
      }
      enum "CR2D00EEGF11" {
        description
          "CR2D00EEGF11.";
      }
      enum "CX6D00EEGF10" {
        description
          "CX6D00EEGF10.";
      }
      enum "CR57EFGFH3" {
        description
          "CR57EFGFH3.";
      }
      enum "CR57L6XFI02" {
        description
          "CR57L6XFI02.";
      }
      enum "CR57LBXFE2" {
        description
          "CR57LBXFE2.";
      }
      enum "CR57E8NCB1" {
        description
          "CR57E8NCB1.";
      }
    }
    description
      "devmHardType";
  }
  typedef devmLoopBackState {
    type enumeration {
      enum "noLoopback" {
        description
          "Loopback none.";
      }
      enum "localLoopback" {
        description
          "Loopback Local.";
      }
      enum "remoteLoopback" {
        description
          "Loopback Remote.";
      }
    }
    description
      "devmLoopBackState";
  }
  typedef devmFlowCtlType {
    type enumeration {
      enum "allEnabled" {
        description
          "All Enabled.";
      }
      enum "receiveEnabled" {
        description
          "Receive Enabled.";
      }
      enum "sendEnabled" {
        description
          "Send Enabled.";
      }
      enum "allDisabled" {
        description
          "All Disabled.";
      }
      enum "defaultConfig" {
        description
          "Default config.";
      }
    }
    description
      "devmFlowCtlType";
  }
  typedef devmtxPowerCfgType {
    type enumeration {
      enum "txPowerTargetValue" {
        description
          "txPowerTargetValue.";
      }
      enum "attenuation" {
        description
          "attenuation.";
      }
      enum "unsupport" {
        description
          "unsupport.";
      }
    }
    description
      "devmtxPowerCfgType";
  }
  typedef devmTxIpgType {
    type enumeration {
      enum "shrink" {
        description
          "shrink.";
      }
      enum "non-shrink" {
        description
          "non-shrink.";
      }
    }
    description
      "devmTxIpgType";
  }
  typedef devmEthFecmodeType {
    type enumeration {
      enum "standard" {
        description
          "standard.";
      }
      enum "none" {
        description
          "none.";
      }
      enum "disable" {
        description
          "disable.";
      }
    }
    description
      "devmEthFecmodeType";
  }
  typedef devmcposclockmodeType {
    type enumeration {
      enum "master" {
        description
          "master.";
      }
      enum "slave" {
        description
          "slave.";
      }
    }
    description
      "devmcposclockmodeType";
  }
  typedef devmcposMapModeType {
    type enumeration {
      enum "h-mode" {
        description
          "h-mode.";
      }
      enum "a-mode" {
        description
          "a-mode.";
      }
      enum "l-mode" {
        description
          "l-mode.";
      }
    }
    description
      "devmcposMapModeType";
  }
  typedef devmcposFrameFormatType {
    type enumeration {
      enum "sdh" {
        description
          "sdh.";
      }
      enum "sonet" {
        description
          "sonet.";
      }
    }
    description
      "devmcposFrameFormatType";
  }
  typedef devmcposMultiplexType {
    type enumeration {
      enum "au-3" {
        description
          "au-3.";
      }
      enum "au-4" {
        description
          "au-4.";
      }
    }
    description
      "devmcposMultiplexType";
  }
  typedef devmcposvc4vc12modeType {
    type enumeration {
      enum "VC4" {
        description
          "VC4.";
      }
      enum "VC12" {
        description
          "VC12.";
      }
    }
    description
      "devmcposvc4vc12modeType";
  }
  typedef devmCposE1ClockModeType {
    type enumeration {
      enum "master" {
        description
          "master.";
      }
      enum "slave" {
        description
          "slave.";
      }
      enum "recovery-domain" {
        description
          "recovery-domain.";
      }
      enum "master-domain" {
        description
          "master-domain.";
      }
    }
    description
      "devmCposE1ClockModeType";
  }
  typedef devmCposE1LoopbackType {
    type enumeration {
      enum "none" {
        description
          "None.";
      }
      enum "local" {
        description
          "local.";
      }
      enum "remote" {
        description
          "remote.";
      }
    }
    description
      "devmCposE1LoopbackType";
  }
  typedef devmCposE1FrameFormatType {
    type enumeration {
      enum "no-crc4" {
        description
          "no CRC4.";
      }
      enum "crc4" {
        description
          "CRC4.";
      }
    }
    description
      "devmCposE1FrameFormatType";
  }
  typedef devmE1T1WorkModeType {
    type enumeration {
      enum "framed" {
        description
          "framed.";
      }
      enum "unframed" {
        description
          "unframed.";
      }
    }
    description
      "devmE1T1WorkModeType";
  }
  typedef devmNegotiationType {
    type enumeration {
      enum "enabled" {
        description
          "Enabled.";
      }
      enum "disabled" {
        description
          "Disabled.";
      }
    }
    description
      "devmNegotiationType";
  }
  typedef devmNegoPatchType {
    type enumeration {
      enum "enabled" {
        description
          "Enabled.";
      }
      enum "disabled" {
        description
          "Disabled.";
      }
      enum "default" {
        description
          "Default.";
      }
    }
    description
      "devmNegoPatchType";
  }
  typedef devmlaserautoshutType {
    type enumeration {
      enum "enable" {
        description
          "enable LAS.";
      }
      enum "disable" {
        description
          "disable LAS.";
      }
    }
    description
      "devmlaserautoshutType";
  }
  typedef devmlaserturnonType {
    type enumeration {
      enum "on" {
        description
          "LaserOpen.";
      }
      enum "off" {
        description
          "LaserClose.";
      }
    }
    description
      "devmlaserturnonType";
  }
  typedef devmPortRateType {
    type enumeration {
      enum "155M" {
        description
          "155M.";
      }
      enum "622M" {
        description
          "622M.";
      }
      enum "notSupport" {
        description
          "NotSupport.";
      }
    }
    description
      "devmPortRateType";
  }
  typedef devmQueuePriorityType {
    type enumeration {
      enum "disable" {
        description
          "disable.";
      }
      enum "enable" {
        description
          "enable.";
      }
      enum "notSupport" {
        description
          "NotSupport.";
      }
    }
    description
      "devmQueuePriorityType";
  }
  typedef devmlaserstatusType {
    type enumeration {
      enum "on" {
        description
          "LaserOn.";
      }
      enum "off" {
        description
          "LaserOff.";
      }
      enum "offline" {
        description
          "LaserOffline.";
      }
    }
    description
      "devmlaserstatusType";
  }
  typedef devmFrameFormatType {
    type enumeration {
      enum "SDH" {
        description
          "SDH.";
      }
      enum "SONET" {
        description
          "SONET.";
      }
    }
    description
      "devmFrameFormatType";
  }
  typedef devmScrambleType {
    type enumeration {
      enum "enabled" {
        description
          "Enabled.";
      }
      enum "disabled" {
        description
          "Disabled.";
      }
    }
    description
      "devmScrambleType";
  }
  typedef devmHoldupType {
    type enumeration {
      enum "enabled" {
        description
          "Enabled.";
      }
      enum "disabled" {
        description
          "Disabled.";
      }
    }
    description
      "devmHoldupType";
  }
  typedef devmSdhClockType {
    type enumeration {
      enum "master" {
        description
          "Master.";
      }
      enum "slave" {
        description
          "Slave.";
      }
    }
    description
      "devmSdhClockType";
  }
  typedef devmSdhFlagModeType {
    type enumeration {
      enum "1byte" {
        description
          "1byte.";
      }
      enum "16byte" {
        description
          "16byte.";
      }
      enum "64byte-or-null-mode" {
        description
          "64byte-or-null-mode.";
      }
      enum "peer" {
        description
          "Peer.";
      }
    }
    description
      "devmSdhFlagModeType";
  }
  typedef devmAtmFlagModeType {
    type enumeration {
      enum "1byte" {
        description
          "1byte.";
      }
      enum "16byte" {
        description
          "16byte.";
      }
      enum "64byte" {
        description
          "64byte.";
      }
      enum "peer" {
        description
          "Peer.";
      }
    }
    description
      "devmAtmFlagModeType";
  }
  typedef devmCPOSSdhFlagModeType {
    type enumeration {
      enum "1byte" {
        description
          "1 byte.";
      }
      enum "16byte" {
        description
          "16 bytes.";
      }
      enum "64byte" {
        description
          "64 bytes.";
      }
    }
    description
      "devmCPOSSdhFlagModeType";
  }
  typedef devmWANSdhFlagModeType {
    type enumeration {
      enum "1byte" {
        description
          "1 byte.";
      }
      enum "16byte" {
        description
          "16 bytes.";
      }
      enum "64byte-or-null-mode" {
        description
          "64byte-or-null-mode.";
      }
    }
    description
      "devmWANSdhFlagModeType";
  }
  typedef devmSdhCRCType {
    type enumeration {
      enum "16" {
        description
          "16Bit.";
      }
      enum "32" {
        description
          "32Bit.";
      }
    }
    description
      "devmSdhCRCType";
  }
  typedef devmE1CRCType {
    type enumeration {
      enum "no-crc4" {
        description
          "No crc4.";
      }
      enum "crc4" {
        description
          "CRC4.";
      }
    }
    description
      "devmE1CRCType";
  }
  typedef devmE1ClockType {
    type enumeration {
      enum "master" {
        description
          "master.";
      }
      enum "slave" {
        description
          "slave.";
      }
    }
    description
      "devmE1ClockType";
  }
  typedef devmE1CodeType {
    type enumeration {
      enum "hdb3" {
        description
          "hdb3.";
      }
      enum "ami" {
        description
          "ami.";
      }
    }
    description
      "devmE1CodeType";
  }
  typedef devmPortLanWanModeType {
    type enumeration {
      enum "lanMode" {
        description
          "LAN Mode.";
      }
      enum "wanMode" {
        description
          "WAN Mode.";
      }
      enum "otnMode" {
        description
          "OTN Mode.";
      }
    }
    description
      "devmPortLanWanModeType";
  }
  typedef devmRemoteportLanWanModeType {
    type enumeration {
      enum "lanMode" {
        description
          "LAN Mode.";
      }
      enum "wanMode" {
        description
          "WAN Mode.";
      }
    }
    description
      "devmRemoteportLanWanModeType";
  }
  typedef devmClockLockStateType {
    type enumeration {
      enum "locked" {
        description
          "";
      }
      enum "unlocked" {
        description
          "";
      }
    }
    description
      "devmClockLockStateType";
  }
  typedef devmClockSwitchModeType {
    type enumeration {
      enum "auto-choice" {
        description
          "auto-choice";
      }
    }
    description
      "devmClockSwitchModeType";
  }
  typedef devmClockSabitType {
    type enumeration {
      enum "unknown" {
        description
          "Unknown.";
      }
      enum "sa4" {
        description
          "sa4.";
      }
      enum "sa5" {
        description
          "sa5.";
      }
      enum "sa6" {
        description
          "sa6.";
      }
      enum "sa7" {
        description
          "sa7.";
      }
      enum "sa8" {
        description
          "sa8.";
      }
    }
    description
      "devmClockSabitType";
  }
  typedef devmClockForceSsmType {
    type enumeration {
      enum "on" {
        description
          "On.";
      }
      enum "off" {
        description
          "Off.";
      }
    }
    description
      "information of enum type devmClockForceSsmType";
  }
  typedef devmClkBitsType {
    type enumeration {
      enum "2mbps" {
        description
          "2mbps.";
      }
      enum "2mhz" {
        description
          "2mhz.";
      }
    }
    description
      "information of enum type devmClkBitsType";
  }
  typedef devmClkBitsMap {
    type enumeration {
      enum "bits0" {
        description
          "bits0.";
      }
      enum "bits1" {
        description
          "bits1.";
      }
      enum "bits2" {
        description
          "bits2.";
      }
      enum "unknown" {
        description
          "Unknown.";
      }
    }
    description
      "information of enum type devmClkBitsMap";
  }
  typedef devmEthSpeedType {
    type enumeration {
      enum "10M" {
        description
          "10M.";
      }
      enum "100M" {
        description
          "100M.";
      }
      enum "155M" {
        description
          "155M.";
      }
      enum "622M" {
        description
          "622M.";
      }
      enum "1000M" {
        description
          "1000M.";
      }
      enum "2500M" {
        description
          "2500M.";
      }
      enum "10G" {
        description
          "10G.";
      }
      enum "40G" {
        description
          "40G.";
      }
      enum "100G" {
        description
          "100G.";
      }
      enum "auto" {
        description
          "Auto.";
      }
    }
    description
      "devmEthSpeedType";
  }
  typedef devmPicEthSpeedType {
    type enumeration {
      enum "10M" {
        description
          "10M";
      }
      enum "100M" {
        description
          "100M";
      }
      enum "auto" {
        description
          "";
      }
    }
    description
      "devmPicEthSpeedType";
  }
  typedef devmPortModeType {
    type enumeration {
      enum "1G" {
        description
          "GE Mode.";
      }
      enum "10G" {
        description
          "10GE Mode.";
      }
      enum "undo" {
        description
          "Cancel Setting.";
      }
    }
    description
      "devmPortModeType";
  }
  typedef devmGfMediaType {
    type enumeration {
      enum "copper" {
        description
          "Copper.";
      }
      enum "fiber100" {
        description
          "Fiber 100M.";
      }
      enum "fiber1000" {
        description
          "Fiber 1000M.";
      }
      enum "auto" {
        description
          "Auto.";
      }
    }
    description
      "devmGfMediaType";
  }
  typedef devmCardInitStatusType {
    type enumeration {
      enum "unknown" {
        description
          "Unknown.";
      }
      enum "success" {
        description
          "Success.";
      }
      enum "fail" {
        description
          "Fail.";
      }
    }
    description
      "devmCardInitStatusType";
  }
  typedef devmCardLogicStatusType {
    type enumeration {
      enum "unknown" {
        description
          "Unknown.";
      }
      enum "success" {
        description
          "Success.";
      }
      enum "fail" {
        description
          "Fail.";
      }
    }
    description
      "devmCardLogicStatusType";
  }
  typedef devmClockSrcStatusType {
    type enumeration {
      enum "unknown" {
        description
          "Unknown.";
      }
      enum "normal" {
        description
          "Normal.";
      }
      enum "abnormal" {
        description
          "Abnormal.";
      }
    }
    description
      "devmClockSrcStatusType";
  }
  typedef devmPortPromodeType {
    type enumeration {
      enum "on" {
        description
          "On.";
      }
      enum "off" {
        description
          "Off.";
      }
    }
    description
      "devmPortPromodeType";
  }
  typedef devmTempVoltStateType {
    type enumeration {
      enum "unknown" {
        description
          "Unknown.";
      }
      enum "normal" {
        description
          "Normal state that maps 'normal' in the command line.";
      }
      enum "minor" {
        description
          "Minor alarm that maps 'minor' in the command line.";
      }
      enum "major" {
        description
          "Major alarm that maps 'fatal' in the command line.";
      }
      enum "fatal" {
        description
          "Fatal.";
      }
    }
    description
      "information of enum type devmTempVoltStateType";
  }
  typedef devmInnerLinkOperStateType {
    type enumeration {
      enum "normal" {
        description
          "Normal.";
      }
      enum "partialFault" {
        description
          "Partial fault.";
      }
      enum "fault" {
        description
          "Fault.";
      }
    }
    description
      "information of enum type devmInnerLinkOperStateType";
  }
  typedef devmInnerLinkAlarmType {
    type enumeration {
      enum "normal" {
        description
          "Normal.";
      }
      enum "partialFault" {
        description
          "Partial fault.";
      }
      enum "fault" {
        description
          "Fault.";
      }
    }
    description
      "information of enum type devmInnerLinkAlarmType";
  }
  typedef devmServerType {
    type enumeration {
      enum "ftp" {
        description
          "FTP.";
      }
      enum "tftp" {
        description
          "TFTP.";
      }
      enum "sftp" {
        description
          "SFTP.";
      }
    }
    description
      "information of enum type devmServerType";
  }
  typedef devmTransType {
    type enumeration {
      enum "put" {
        description
          "PUT.";
      }
      enum "get" {
        description
          "GET.";
      }
    }
    description
      "information of enum type devmTransType";
  }
  typedef devmPreferKexType {
    type enumeration {
      enum "dhExchangeGroup" {
        description
          "KEX_DH_EXCHANGE_GROUP.";
      }
      enum "dhGroup1" {
        description
          "KEX_DH_GROUP1.";
      }
    }
    description
      "information of enum type devmPreferKexType";
  }
  typedef devmCipherType {
    type enumeration {
      enum "aes128" {
        description
          "AES128.";
      }
    }
    description
      "information of enum type devmCipherType";
  }
  typedef devmStocHmacType {
    type enumeration {
      enum "md5" {
        description
          "MD5.";
      }
      enum "md5_96" {
        description
          "MD5_96.";
      }
      enum "sha1" {
        description
          "SHA1.";
      }
      enum "sha1_96" {
        description
          "SHA1_96.";
      }
    }
    description
      "information of enum type devmStocHmacType";
  }
  typedef devm_transAlarmType_type {
    type enumeration {
      enum "LOS" {
        description
          "LOS.";
      }
      enum "LAIS" {
        description
          "LAIS.";
      }
      enum "LOF" {
        description
          "LOF.";
      }
      enum "OOF" {
        description
          "OOF.";
      }
      enum "AUAIS" {
        description
          "AUAIS.";
      }
      enum "B3TCA" {
        description
          "B3TCA.";
      }
      enum "B1TCA" {
        description
          "B1TCA.";
      }
      enum "B2TCA" {
        description
          "B2TCA.";
      }
      enum "LOM" {
        description
          "LOM.";
      }
      enum "LOP" {
        description
          "LOP.";
      }
      enum "LRDI" {
        description
          "LRDI.";
      }
      enum "LREI" {
        description
          "LREI.";
      }
      enum "PAIS" {
        description
          "PAIS.";
      }
      enum "PRDI" {
        description
          "PRDI.";
      }
      enum "PREI" {
        description
          "PREI.";
      }
      enum "PPLM" {
        description
          "PPLM.";
      }
      enum "RDOOL" {
        description
          "RDOOL.";
      }
      enum "RROOL" {
        description
          "RROOL.";
      }
      enum "SDBERE" {
        description
          "SDBERE.";
      }
      enum "SFBERE" {
        description
          "SFBERE.";
      }
      enum "TROOL" {
        description
          "TROOL.";
      }
      enum "PUNEQ" {
        description
          "PUNEQ.";
      }
      enum "LCD" {
        description
          "LCD.";
      }
      enum "WLNK" {
        description
          "WLNK.";
      }
      enum "ODU_AIS" {
        description
          "ODU_AIS.";
      }
      enum "ODU_LCK" {
        description
          "ODU_LCK.";
      }
      enum "ODU_OCI" {
        description
          "ODU_OCI.";
      }
      enum "OTU_AIS" {
        description
          "OTU_AIS.";
      }
      enum "OTU_LOM" {
        description
          "OTU_LOM.";
      }
      enum "OTU_SD_BER" {
        description
          "OTU_SD_BER.";
      }
      enum "OTU_SF_BER" {
        description
          "OTU_SF_BER.";
      }
      enum "PM_BDI" {
        description
          "PM_BDI.";
      }
      enum "PM_TIM" {
        description
          "PM_TIM.";
      }
      enum "R_LOF" {
        description
          "R_LOF.";
      }
      enum "R_LOS" {
        description
          "R_LOS.";
      }
      enum "R_OOF" {
        description
          "R_OOF.";
      }
      enum "SM_BDI" {
        description
          "SM_BDI.";
      }
      enum "SM_IAE" {
        description
          "SM_IAE.";
      }
      enum "SM_TIM" {
        description
          "SM_TIM.";
      }
    }
    description
      "devm_transAlarmType_type";
  }
  typedef devmTrapType {
    type enumeration {
      enum "base-trap" {
        description
          "base-trap.";
      }
      enum "dc-trap" {
        description
          "dc-trap.";
      }
      enum "entity-trap" {
        description
          "entity-trap.";
      }
    }
    description
      "devmTrapType";
  }
  typedef devmOpticalType {
    type enumeration {
      enum "unknown" {
        description
          "Unknown.";
      }
      enum "sc" {
        description
          "sc.";
      }
      enum "gbic" {
        description
          "gbic.";
      }
      enum "sfp" {
        description
          "sfp.";
      }
      enum "esfp" {
        description
          "esfp.";
      }
      enum "copper" {
        description
          "copper.";
      }
      enum "xfp" {
        description
          "xfp.";
      }
      enum "xenpak" {
        description
          "xenpak.";
      }
      enum "transponder" {
        description
          "transponder.";
      }
      enum "cfp" {
        description
          "cfp.";
      }
      enum "smb" {
        description
          "smb.";
      }
      enum "sfp+" {
        description
          "sfp+.";
      }
      enum "cxp" {
        description
          "cxp.";
      }
      enum "qsfp" {
        description
          "qsfp.";
      }
      enum "qsfp+" {
        description
          "qsfp+.";
      }
      enum "cfp2" {
        description
          "cfp2.";
      }
      enum "dwdmsfp" {
        description
          "dwdmsfp.";
      }
      enum "msa100glh" {
        description
          "msa100glh.";
      }
      enum "gps" {
        description
          "gps.";
      }
      enum "cfp4" {
        description
          "cfp4.";
      }
      enum "qsfp28" {
        description
          "qsfp28.";
      }
      enum "csfp" {
        description
          "csfp.";
      }
      enum "sfp_sfp+" {
        description
          "sfp_sfp+.";
      }
    }
    description
      "devmOpticalType";
  }
  typedef devmOpticalFiberType {
    type enumeration {
      enum "unknown" {
        description
          "Unknown.";
      }
      enum "sc" {
        description
          "sc.";
      }
      enum "style_1_copper_connector" {
        description
          "style_1_copper_connector.";
      }
      enum "style_2_copper_connector" {
        description
          "style_2_copper_connector.";
      }
      enum "bnc_tnc" {
        description
          "bnc_tnc.";
      }
      enum "coaxial_headers" {
        description
          "coaxial_headers.";
      }
      enum "fiberJack" {
        description
          "fiberJack.";
      }
      enum "lc" {
        description
          "lc.";
      }
      enum "mt-rj" {
        description
          "mt-rj.";
      }
      enum "mu" {
        description
          "mu.";
      }
      enum "sg" {
        description
          "sg.";
      }
      enum "optical_pigtail" {
        description
          "optical_pigtail.";
      }
      enum "hssdcII" {
        description
          "hssdcII.";
      }
      enum "copper_pigtail" {
        description
          "copper_pigtail.";
      }
      enum "MPO" {
        description
          "MPO.";
      }
    }
    description
      "devmOpticalFiberType";
  }
  typedef devmSysWorkType {
    type enumeration {
      enum "unknown" {
        description
          "Unknown.";
      }
      enum "redundant" {
        description
          "Redundant mode.";
      }
      enum "non-redundant" {
        description
          "Non-redundant mode.";
      }
    }
    description
      "information of enum type devmSysWorkType";
  }
  typedef devmForwardWorkType {
    type enumeration {
      enum "unknown" {
        description
          "Unknown.";
      }
      enum "compatible" {
        description
          "compatible mode.";
      }
      enum "enhance" {
        description
          "enhance mode.";
      }
    }
    description
      "information of enum type devmForwardWorkType";
  }
  typedef devmCmuAlmMode {
    type enumeration {
      enum "open" {
        description
          "open.";
      }
      enum "close" {
        description
          "close.";
      }
      enum "undo" {
        description
          "undo.";
      }
    }
    description
      "information of enum type devmCmuAlmMode";
  }
  typedef devmCmuSwitchFog {
    type enumeration {
      enum "fog" {
        description
          "fog.";
      }
      enum "unknown" {
        description
          "Unknown.";
      }
    }
    description
      "information of enum type devmCmuSwitchFog";
  }
  typedef devmCmuSwitchName {
    type enumeration {
      enum "unknown" {
        description
          "Unknown.";
      }
      enum "voltage" {
        description
          "CMU Voltage.";
      }
      enum "door" {
        description
          "CMU Door.";
      }
      enum "humidity" {
        description
          "CMU Humidity.";
      }
      enum "fog" {
        description
          "CMU Fog.";
      }
      enum "temperature" {
        description
          "CMU Temperature.";
      }
    }
    description
      "information of enum type devmCmuSwitchName";
  }
  typedef devmAnalogType {
    type enumeration {
      enum "unknown" {
        description
          "Unknown.";
      }
      enum "current" {
        description
          "current.";
      }
      enum "voltage" {
        description
          "voltage.";
      }
    }
    description
      "information of enum type devmAnalogType";
  }
  typedef devmAnalogObjectType {
    type enumeration {
      enum "unknown" {
        description
          "Unknown.";
      }
      enum "temperature" {
        description
          "temperature.";
      }
      enum "humidity" {
        description
          "humidity.";
      }
    }
    description
      "information of enum type devmAnalogObjectType";
  }
  typedef devmProductType {
    type enumeration {
      enum "unknown" {
        description
          "Unknown.";
      }
      enum "single" {
        description
          "Single.";
      }
      enum "ccc-0" {
        description
          "CCC-0.";
      }
      enum "ccc-1" {
        description
          "CCC-1.";
      }
      enum "ccc-2" {
        description
          "CCC-2.";
      }
    }
    description
      "information of enum type devmProductType";
  }
  typedef energyModeType {
    type enumeration {
      enum "basic" {
        description
          "basic.";
      }
      enum "standard" {
        description
          "standard.";
      }
      enum "deep" {
        description
          "deep.";
      }
      enum "optimal" {
        description
          "optimal.";
      }
    }
    description
      "information of enum type energyModeType";
  }
  typedef mibQueryModeType {
    type enumeration {
      enum "default" {
        description
          "NO.";
      }
      enum "brief" {
        description
          "YES.";
      }
    }
    description
      "information of enum type mibQueryModeType";
  }
  typedef pwrSupplyModeType {
    type enumeration {
      enum "standard" {
        description
          "standard";
      }
      enum "assign" {
        description
          "assign";
      }
    }
    description
      "information of enum type pwrSupplyModeType";
  }
  typedef pwrSupplyTempType {
    type enumeration {
      enum "templow" {
        description
          "40.0";
      }
      enum "temphigh" {
        description
          "55.0";
      }
    }
    description
      "information of enum type pwrSupplyTempType";
  }
  typedef warmBackUpModeCfgType {
    type enumeration {
      enum "disable" {
        description
          "undo warm-backup mode enable";
      }
      enum "enable" {
        description
          "warm-backup mode enable";
      }
    }
    description
      "information of enum type warmBackUpModeCfgType";
  }
  typedef warmBackUpModeStsType {
    type enumeration {
      enum "off" {
        description
          "warm-backup status : off";
      }
      enum "on" {
        description
          "warm-backup status : on";
      }
    }
    description
      "information of enum type warmBackUpModeStsType";
  }
  typedef e3t3FlagType {
    type enumeration {
      enum "E3" {
        description
          "E3.";
      }
      enum "T3" {
        description
          "T3.";
      }
    }
    description
      "e3t3FlagType";
  }
  typedef e3t3FrameFormat {
    type enumeration {
      enum "G.751" {
        description
          "G.751.";
      }
      enum "none" {
        description
          "none.";
      }
    }
    description
      "e3t3FrameFormat";
  }
  typedef devmHalfChassisPos {
    type enumeration {
      enum "upper" {
        description
          "CCC upper chassis";
      }
      enum "lower" {
        description
          "CCC lower chassis";
      }
    }
    description
      "information of enum type devmHalfChassisPos";
  }
  typedef devmFiberConnType {
    type enumeration {
      enum "quarterFabric" {
        description
          "Quarter type of Fiber Connection  ";
      }
      enum "halfFabric" {
        description
          "Half type of Fiber Connection ";
      }
      enum "fullFabric" {
        description
          "Full type of Fiber Connection";
      }
    }
    description
      "devmFiberConnType";
  }
  typedef devmTrafficState {
    type enumeration {
      enum "open" {
        description
          "open state";
      }
      enum "close" {
        description
          "close state";
      }
    }
    description
      "information of enum type devmTrafficState";
  }
  typedef slotForwardModeType {
    type enumeration {
      enum "Loopback" {
        description
          "Loopback";
      }
      enum "Through" {
        description
          "Through";
      }
      enum "Invalid" {
        description
          "Invalid";
      }
    }
    description
      "slot forward mode";
  }
  typedef devmOpticalTunableType {
    type enumeration {
      enum "notSupported" {
        description
          "Not supported.";
      }
      enum "notTunable" {
        description
          "Not tunable.";
      }
      enum "tunable" {
        description
          "Tunable.";
      }
      enum "supported" {
        description
          "Supported.";
      }
    }
    description
      "devmOpticalTunableType";
  }
  typedef devmOpticalDirectionType {
    type enumeration {
      enum "notSupported" {
        description
          "Not supported.";
      }
      enum "twoFiberBidirection" {
        description
          "Two fiber Bi direction.";
      }
      enum "oneFiberBidirection" {
        description
          "One fiber Bi direction.";
      }
      enum "twoFiberTwoPortBidirection" {
        description
          "Two fiber two port Bi direction.";
      }
    }
    description
      "devmOpticalDirectionType";
  }
  typedef devmBitErrorType {
    type enumeration {
      enum "No-configurable" {
        description
          "Not configurable.";
      }
      enum "crc" {
        description
          "crc error.";
      }
      enum "prefec" {
        description
          "prefec error.";
      }
    }
    description
      "devmBitErrorType";
  }
  typedef devmTunableWaveLengthType {
    type enumeration {
      enum "No-configurable" {
        description
          "No configuration.";
      }
      enum "C-band:80-192.10THz-1560.606nm" {
        description
          "C-band:80-192.10THz-1560.606nm.";
      }
      enum "C-band:79-192.15THz-1560.200nm" {
        description
          "C-band:79-192.15THz-1560.200nm.";
      }
      enum "C-band:78-192.20THz-1559.794nm" {
        description
          "C-band:78-192.20THz-1559.794nm.";
      }
      enum "C-band:77-192.25THz-1559.389nm" {
        description
          "C-band:77-192.25THz-1559.389nm.";
      }
      enum "C-band:76-192.30THz-1558.983nm" {
        description
          "C-band:76-192.30THz-1558.983nm.";
      }
      enum "C-band:75-192.35THz-1558.578nm" {
        description
          "C-band:75-192.35THz-1558.578nm.";
      }
      enum "C-band:74-192.40THz-1558.173nm" {
        description
          "C-band:74-192.40THz-1558.173nm.";
      }
      enum "C-band:73-192.45THz-1557.768nm" {
        description
          "C-band:73-192.45THz-1557.768nm.";
      }
      enum "C-band:72-192.50THz-1557.363nm" {
        description
          "C-band:72-192.50THz-1557.363nm.";
      }
      enum "C-band:71-192.55THz-1556.959nm" {
        description
          "C-band:71-192.55THz-1556.959nm.";
      }
      enum "C-band:70-192.60THz-1556.555nm" {
        description
          "C-band:70-192.60THz-1556.555nm.";
      }
      enum "C-band:69-192.65THz-1556.151nm" {
        description
          "C-band:69-192.65THz-1556.151nm.";
      }
      enum "C-band:68-192.70THz-1555.747nm" {
        description
          "C-band:68-192.70THz-1555.747nm.";
      }
      enum "C-band:67-192.75THz-1555.343nm" {
        description
          "C-band:67-192.75THz-1555.343nm.";
      }
      enum "C-band:66-192.80THz-1554.940nm" {
        description
          "C-band:66-192.80THz-1554.940nm.";
      }
      enum "C-band:65-192.85THz-1554.537nm" {
        description
          "C-band:65-192.85THz-1554.537nm.";
      }
      enum "C-band:64-192.90THz-1554.134nm" {
        description
          "C-band:64-192.90THz-1554.134nm.";
      }
      enum "C-band:63-192.95THz-1553.731nm" {
        description
          "C-band:63-192.95THz-1553.731nm.";
      }
      enum "C-band:62-193.00THz-1553.329nm" {
        description
          "C-band:62-193.00THz-1553.329nm.";
      }
      enum "C-band:61-193.05THz-1552.926nm" {
        description
          "C-band:61-193.05THz-1552.926nm.";
      }
      enum "C-band:60-193.10THz-1552.524nm" {
        description
          "C-band:60-193.10THz-1552.524nm.";
      }
      enum "C-band:59-193.15THz-1552.122nm" {
        description
          "C-band:59-193.15THz-1552.122nm.";
      }
      enum "C-band:58-193.20THz-1551.721nm" {
        description
          "C-band:58-193.20THz-1551.721nm.";
      }
      enum "C-band:57-193.25THz-1551.319nm" {
        description
          "C-band:57-193.25THz-1551.319nm.";
      }
      enum "C-band:56-193.30THz-1550.918nm" {
        description
          "C-band:56-193.30THz-1550.918nm.";
      }
      enum "C-band:55-193.35THz-1550.517nm" {
        description
          "C-band:55-193.35THz-1550.517nm.";
      }
      enum "C-band:54-193.40THz-1550.116nm" {
        description
          "C-band:54-193.40THz-1550.116nm.";
      }
      enum "C-band:53-193.45THz-1549.715nm" {
        description
          "C-band:53-193.45THz-1549.715nm.";
      }
      enum "C-band:52-193.50THz-1549.315nm" {
        description
          "C-band:52-193.50THz-1549.315nm.";
      }
      enum "C-band:51-193.55THz-1548.915nm" {
        description
          "C-band:51-193.55THz-1548.915nm.";
      }
      enum "C-band:50-193.60THz-1548.515nm" {
        description
          "C-band:50-193.60THz-1548.515nm.";
      }
      enum "C-band:49-193.65THz-1548.115nm" {
        description
          "C-band:49-193.65THz-1548.115nm.";
      }
      enum "C-band:48-193.70THz-1547.715nm" {
        description
          "C-band:48-193.70THz-1547.715nm.";
      }
      enum "C-band:47-193.75THz-1547.316nm" {
        description
          "C-band:47-193.75THz-1547.316nm.";
      }
      enum "C-band:46-193.80THz-1546.917nm" {
        description
          "C-band:46-193.80THz-1546.917nm.";
      }
      enum "C-band:45-193.85THz-1546.518nm" {
        description
          "C-band:45-193.85THz-1546.518nm.";
      }
      enum "C-band:44-193.90THz-1546.119nm" {
        description
          "C-band:44-193.90THz-1546.119nm.";
      }
      enum "C-band:43-193.95THz-1545.720nm" {
        description
          "C-band:43-193.95THz-1545.720nm.";
      }
      enum "C-band:42-194.00THz-1545.322nm" {
        description
          "C-band:42-194.00THz-1545.322nm.";
      }
      enum "C-band:41-194.05THz-1544.924nm" {
        description
          "C-band:41-194.05THz-1544.924nm.";
      }
      enum "C-band:40-194.10THz-1544.526nm" {
        description
          "C-band:40-194.10THz-1544.526nm.";
      }
      enum "C-band:39-194.15THz-1544.128nm" {
        description
          "C-band:39-194.15THz-1544.128nm.";
      }
      enum "C-band:38-194.20THz-1543.730nm" {
        description
          "C-band:38-194.20THz-1543.730nm.";
      }
      enum "C-band:37-194.25THz-1543.333nm" {
        description
          "C-band:37-194.25THz-1543.333nm.";
      }
      enum "C-band:36-194.30THz-1542.936nm" {
        description
          "C-band:36-194.30THz-1542.936nm.";
      }
      enum "C-band:35-194.35THz-1542.539nm" {
        description
          "C-band:35-194.35THz-1542.539nm.";
      }
      enum "C-band:34-194.40THz-1542.142nm" {
        description
          "C-band:34-194.40THz-1542.142nm.";
      }
      enum "C-band:33-194.45THz-1541.746nm" {
        description
          "C-band:33-194.45THz-1541.746nm.";
      }
      enum "C-band:32-194.50THz-1541.349nm" {
        description
          "C-band:32-194.50THz-1541.349nm.";
      }
      enum "C-band:31-194.55THz-1540.953nm" {
        description
          "C-band:31-194.55THz-1540.953nm.";
      }
      enum "C-band:30-194.60THz-1540.557nm" {
        description
          "C-band:30-194.60THz-1540.557nm.";
      }
      enum "C-band:29-194.65THz-1540.162nm" {
        description
          "C-band:29-194.65THz-1540.162nm.";
      }
      enum "C-band:28-194.70THz-1539.766nm" {
        description
          "C-band:28-194.70THz-1539.766nm.";
      }
      enum "C-band:27-194.75THz-1539.371nm" {
        description
          "C-band:27-194.75THz-1539.371nm.";
      }
      enum "C-band:26-194.80THz-1538.976nm" {
        description
          "C-band:26-194.80THz-1538.976nm.";
      }
      enum "C-band:25-194.85THz-1538.581nm" {
        description
          "C-band:25-194.85THz-1538.581nm.";
      }
      enum "C-band:24-194.90THz-1538.186nm" {
        description
          "C-band:24-194.90THz-1538.186nm.";
      }
      enum "C-band:23-194.95THz-1537.792nm" {
        description
          "C-band:23-194.95THz-1537.792nm.";
      }
      enum "C-band:22-195.00THz-1537.397nm" {
        description
          "C-band:22-195.00THz-1537.397nm.";
      }
      enum "C-band:21-195.05THz-1537.003nm" {
        description
          "C-band:21-195.05THz-1537.003nm.";
      }
      enum "C-band:20-195.10THz-1536.609nm" {
        description
          "C-band:20-195.10THz-1536.609nm.";
      }
      enum "C-band:19-195.15THz-1536.216nm" {
        description
          "C-band:19-195.15THz-1536.216nm.";
      }
      enum "C-band:18-195.20THz-1535.822nm" {
        description
          "C-band:18-195.20THz-1535.822nm.";
      }
      enum "C-band:17-195.25THz-1535.429nm" {
        description
          "C-band:17-195.25THz-1535.429nm.";
      }
      enum "C-band:16-195.30THz-1535.036nm" {
        description
          "C-band:16-195.30THz-1535.036nm.";
      }
      enum "C-band:15-195.35THz-1534.643nm" {
        description
          "C-band:15-195.35THz-1534.643nm.";
      }
      enum "C-band:14-195.40THz-1534.250nm" {
        description
          "C-band:14-195.40THz-1534.250nm.";
      }
      enum "C-band:13-195.45THz-1533.858nm" {
        description
          "C-band:13-195.45THz-1533.858nm.";
      }
      enum "C-band:12-195.50THz-1533.465nm" {
        description
          "C-band:12-195.50THz-1533.465nm.";
      }
      enum "C-band:11-195.55THz-1533.073nm" {
        description
          "C-band:11-195.55THz-1533.073nm.";
      }
      enum "C-band:10-195.60THz-1532.681nm" {
        description
          "C-band:10-195.60THz-1532.681nm.";
      }
      enum "C-band:09-195.65THz-1532.290nm" {
        description
          "C-band:09-195.65THz-1532.290nm.";
      }
      enum "C-band:08-195.70THz-1531.898nm" {
        description
          "C-band:08-195.70THz-1531.898nm.";
      }
      enum "C-band:07-195.75THz-1531.507nm" {
        description
          "C-band:07-195.75THz-1531.507nm.";
      }
      enum "C-band:06-195.80THz-1531.116nm" {
        description
          "C-band:06-195.80THz-1531.116nm.";
      }
      enum "C-band:05-195.85THz-1530.725nm" {
        description
          "C-band:05-195.85THz-1530.725nm.";
      }
      enum "C-band:04-195.90THz-1530.334nm" {
        description
          "C-band:04-195.90THz-1530.334nm.";
      }
      enum "C-band:03-195.95THz-1529.944nm" {
        description
          "C-band:03-195.95THz-1529.944nm.";
      }
      enum "C-band:02-196.00THz-1529.553nm" {
        description
          "C-band:02-196.00THz-1529.553nm.";
      }
      enum "C-band:01-196.05THz-1529.163nm" {
        description
          "C-band:01-196.05THz-1529.163nm.";
      }
    }
    description
      "devmTunableWaveLengthType";
  }
  typedef devmTriggerTimeType {
    type enumeration {
      enum "No-configurable" {
        description
          "Not configurable.";
      }
      enum "second" {
        description
          "second.";
      }
      enum "200ms" {
        description
          "200ms.";
      }
    }
    description
      "devmTriggerTimeType";
  }
  typedef portBandwidthType {
    type enumeration {
      enum "Physical" {
        description
          "Physical.";
      }
      enum "DataLink" {
        description
          "DataLink.";
      }
    }
    description
      "portBandwidthType";
  }
  typedef devmInsertAisAlmType {
    type enumeration {
      enum "hptim" {
        description
          "hptim.";
      }
      enum "lptim" {
        description
          "lptim.";
      }
      enum "rstim" {
        description
          "rstim.";
      }
      enum "hptimatm" {
        description
          "hptimatm.";
      }
      enum "hpuneqatm" {
        description
          "hpuneqatm.";
      }
    }
    description
      "devmInsertAisAlmType";
  }
  typedef devmPortFaultType {
    type enumeration {
      enum "unSupported" {
        description
          "unsupported.";
      }
      enum "normal" {
        description
          "normal.";
      }
      enum "fault" {
        description
          "fault.";
      }
    }
    description
      "devmPortFaultType";
  }
  typedef devmSdhAlarmStatusType {
    type enumeration {
      enum "unSupported" {
        description
          "unSupported";
      }
      enum "normal" {
        description
          "normal";
      }
      enum "alarm" {
        description
          "alarm";
      }
    }
    description
      "devmSdhAlarmStatusType";
  }
  typedef devmnegoModeType {
    type enumeration {
      enum "NA" {
        description
          "NA.";
      }
      enum "Slave" {
        description
          "Slave.";
      }
    }
    description
      "devmnegoModeType";
  }
  typedef devmVsuSerType {
    type enumeration {
      enum "hts" {
        description
          "hts.";
      }
    }
    description
      "information of enum type devmVsuSerType";
  }
  typedef devmFecModeType {
    type enumeration {
      enum "standard" {
        description
          "standard.";
      }
      enum "none" {
        description
          "none.";
      }
      enum "enhanced" {
        description
          "enhanced.";
      }
      enum "enhanced-i-4" {
        description
          "enhanced-i-4.";
      }
      enum "enhanced-i-7" {
        description
          "enhanced-i-7.";
      }
    }
    description
      "devmFecModeType";
  }
  typedef devmSplitTypeEnum {
    type enumeration {
      enum "none" {
        description
          "none.";
      }
      enum "4*10GE" {
        description
          "4*10GE.";
      }
      enum "1*100GE" {
        description
          "1*100GE.";
      }
      enum "10*10GE" {
        description
          "10*10GE.";
      }
      enum "1*40GE" {
        description
          "1*40GE.";
      }
    }
    description
      "devmSplitTypeEnum";
  }
  typedef devmcardBandModeType {
    type enumeration {
      enum "unSupported" {
        description
          "UnSupported.";
      }
      enum "ETH-28X10GF" {
        description
          "ETH-28X10GF.";
      }
      enum "ETH-26X10GF-18XGF" {
        description
          "ETH-26X10GF-18XGF.";
      }
      enum "ETH-20X10GF-24XGF" {
        description
          "ETH-20X10GF-24XGF.";
      }
    }
    description
      "devmcardBandModeType";
  }
  typedef slotLinkProtCfgState {
    type enumeration {
      enum "enable" {
        description
          "Enabled.";
      }
      enum "disable" {
        description
          "Disabled.";
      }
    }
    description
      "information of enum type slotLinkProtCfgState";
  }
  typedef devmclockType {
    type enumeration {
      enum "syn-clock" {
        description
          "syn-clock.";
      }
      enum "line-clock" {
        description
          "line-clock.";
      }
    }
    description
      "information of enum type devmclockType";
  }
  typedef devmboardDevType {
    type enumeration {
      enum "LPU" {
        description
          "LPU.";
      }
      enum "SFU" {
        description
          "SFU.";
      }
    }
    description
      "information of enum type devmboardDevType";
  }
  typedef devmswitchModeType {
    type enumeration {
      enum "Auto-choice" {
        description
          "Auto-choice.";
      }
      enum "Force-choice" {
        description
          "Force-choice.";
      }
    }
    description
      "information of enum type devmswitchModeType";
  }
  typedef devmlockStatType {
    type enumeration {
      enum "Locked" {
        description
          "Locked.";
      }
      enum "Unlocked" {
        description
          "Unlocked.";
      }
    }
    description
      "information of enum type devmlockStatType";
  }
  typedef devmintfMatchCheckNodeObject {
    type enumeration {
      enum "card" {
        description
          "card.";
      }
      enum "board" {
        description
          "board.";
      }
      enum "chassis" {
        description
          "chassis.";
      }
    }
    description
      "devmintfMatchCheckNodeObject";
  }
  typedef devmintfMatchCheckNodeFlag {
    type enumeration {
      enum "enable" {
        description
          "enable.";
      }
      enum "disable" {
        description
          "disable.";
      }
    }
    description
      "devmintfMatchCheckNodeFlag";
  }
  typedef devmupglpuByTestbusBrdType {
    type enumeration {
      enum "LPU" {
        description
          "LPU.";
      }
    }
    description
      "devmupglpuByTestbusBrdType";
  }
  typedef devmupglpuByTestbusProcType {
    type enumeration {
      enum "lpu-bootload" {
        description
          "lpu-bootload.";
      }
      enum "lpu-bootrom" {
        description
          "lpu-bootrom.";
      }
      enum "lpu-epld" {
        description
          "lpu-epld.";
      }
      enum "lpu-epld2" {
        description
          "lpu-epld2.";
      }
      enum "lpu-epld3" {
        description
          "lpu-epld3.";
      }
      enum "lpu-rcw" {
        description
          "lpu-rcw.";
      }
      enum "pic0-epld" {
        description
          "pic0-epld.";
      }
      enum "pic0-pwr-epld" {
        description
          "pic0-pwr-epld.";
      }
      enum "pic1-epld" {
        description
          "pic1-epld.";
      }
      enum "pic1-pwr-epld" {
        description
          "pic1-pwr-epld.";
      }
      enum "pwr-epld" {
        description
          "pwr-epld.";
      }
      enum "vsuf-dp1-boot" {
        description
          "vsuf-dp1-boot.";
      }
      enum "vsuf-dp2-boot" {
        description
          "vsuf-dp2-boot.";
      }
      enum "vsuf-dp3-boot" {
        description
          "vsuf-dp3-boot.";
      }
      enum "vsuf-dp4-boot" {
        description
          "vsuf-dp4-boot.";
      }
    }
    description
      "devmupglpuByTestbusProcType";
  }
  typedef devmupgmpuByTestbusBrdType {
    type enumeration {
      enum "MPU" {
        description
          "MPU.";
      }
    }
    description
      "devmupgmpuByTestbusBrdType";
  }
  typedef devmupgmpuByTestbusProcType {
    type enumeration {
      enum "bootload" {
        description
          "bootload";
      }
      enum "bootrom" {
        description
          "bootrom.";
      }
      enum "inner-epld" {
        description
          "inner-epld.";
      }
      enum "software" {
        description
          "software.";
      }
      enum "me" {
        description
          "me";
      }
      enum "mpu-epld" {
        description
          "mpu-epld";
      }
      enum "pwr-epld" {
        description
          "pwr-epld";
      }
    }
    description
      "devmupgmpuByTestbusProcType";
  }
  typedef devmupgsfuByTestbusBrdType {
    type enumeration {
      enum "SFU" {
        description
          "SFU.";
      }
    }
    description
      "devmupgsfuByTestbusBrdType";
  }
  typedef devmupgsfuByTestbusProcType {
    type enumeration {
      enum "sfu-bootload" {
        description
          "sfu-bootload.";
      }
      enum "sfu-bootrom" {
        description
          "sfu-bootrom.";
      }
      enum "sfu-epld1" {
        description
          "sfu-epld1.";
      }
      enum "sfu-epld2" {
        description
          "sfu-epld2.";
      }
      enum "pwr-epld" {
        description
          "pwr-epld";
      }
    }
    description
      "devmupgsfuByTestbusProcType";
  }
  typedef devmupgipuByTestbusBrdType {
    type enumeration {
      enum "IPU" {
        description
          "IPU.";
      }
    }
    description
      "devmupgipuByTestbusBrdType";
  }
  typedef devmupgipuByTestbusProcType {
    type enumeration {
      enum "pic-epld" {
        description
          "pic-epld.";
      }
    }
    description
      "devmupgipuByTestbusProcType";
  }
  typedef devmupgcmuByTestbusBrdType {
    type enumeration {
      enum "CMU" {
        description
          "CMU.";
      }
    }
    description
      "devmupgcmuByTestbusBrdType";
  }
  typedef devmupgcmuByTestbusProcType {
    type enumeration {
      enum "cmu-epld" {
        description
          "cmu-epld";
      }
      enum "cmu-bios" {
        description
          "cmu-bios";
      }
    }
    description
      "devmupgcmuByTestbusProcType";
  }
  typedef devmmpuType {
    type enumeration {
      enum "MPU" {
        description
          "MPU.";
      }
    }
    description
      "devmmpuType";
  }
  typedef devmlpuType {
    type enumeration {
      enum "LPU" {
        description
          "LPU.";
      }
    }
    description
      "devmlpuType";
  }
  typedef devmsfuType {
    type enumeration {
      enum "SFU" {
        description
          "SFU.";
      }
    }
    description
      "devmsfuType";
  }
  typedef devmfanType {
    type enumeration {
      enum "FAN" {
        description
          "FAN.";
      }
    }
    description
      "devmfanType";
  }
  typedef devmlcdType {
    type enumeration {
      enum "LCD" {
        description
          "LCD.";
      }
    }
    description
      "devmlcdType";
  }
  typedef devmecuType {
    type enumeration {
      enum "ECU" {
        description
          "ECU.";
      }
    }
    description
      "devmecuType";
  }
  typedef devmicuType {
    type enumeration {
      enum "ICU" {
        description
          "ICU.";
      }
    }
    description
      "devmicuType";
  }
  typedef devmcmuType {
    type enumeration {
      enum "CMU" {
        description
          "CMU.";
      }
    }
    description
      "devmcmuType";
  }
  typedef devmpmuType {
    type enumeration {
      enum "PMU" {
        description
          "PMU.";
      }
    }
    description
      "devmpmuType";
  }
  typedef devmipuType {
    type enumeration {
      enum "IPU" {
        description
          "IPU.";
      }
    }
    description
      "devmipuType";
  }
  typedef devmallslotType {
    type enumeration {
      enum "All-Slot" {
        description
          "All-Slot.";
      }
    }
    description
      "devmallslotType";
  }
  typedef devmbrdType {
    type enumeration {
      enum "MPU" {
        description
          "MPU.";
      }
      enum "LPU" {
        description
          "LPU.";
      }
      enum "FAN" {
        description
          "FAN.";
      }
      enum "SFU" {
        description
          "SFU.";
      }
      enum "LCD" {
        description
          "LCD.";
      }
      enum "ICU" {
        description
          "ICU.";
      }
      enum "ECU" {
        description
          "ECU.";
      }
    }
    description
      "devmbrdType";
  }
  typedef devmoperType {
    type enumeration {
      enum "bootrom" {
        description
          "bootrom.";
      }
      enum "monitorbus" {
        description
          "monitorbus.";
      }
      enum "firmware" {
        description
          "firmware.";
      }
      enum "all-item" {
        description
          "all-item.";
      }
    }
    description
      "devmoperType";
  }
  typedef devmlocType {
    type enumeration {
      enum "monitorbus" {
        description
          "monitorbus.";
      }
    }
    description
      "devmlocType";
  }
  typedef devmStatus {
    type enumeration {
      enum "YES" {
        description
          "YES.";
      }
      enum "NO" {
        description
          "NO.";
      }
    }
    description
      "devmStatus";
  }
  typedef devmupgmpuByTestbusType {
    type enumeration {
      enum "bootload" {
        description
          "bootload.";
      }
      enum "bootrom" {
        description
          "bootrom.";
      }
      enum "mpu-epld" {
        description
          "mpu-epld.";
      }
    }
    description
      "devmupgmpuByTestbusType";
  }
  typedef devmupglpuByTestbusType {
    type enumeration {
      enum "lpu-bootload" {
        description
          "lpu-bootload";
      }
      enum "lpu-bootrom" {
        description
          "lpu-bootrom";
      }
      enum "lpu-epld" {
        description
          "lpu-epld";
      }
      enum "lpu-power-epld0" {
        description
          "lpu-power-epld0";
      }
      enum "lpu-power-epld1" {
        description
          "lpu-power-epld1";
      }
      enum "pic-epld" {
        description
          "pic-epld";
      }
    }
    description
      "devmupglpuByTestbusType";
  }
  typedef sfuSwitchModeType {
    type enumeration {
      enum "enable" {
        description
          "Enable.";
      }
      enum "disable" {
        description
          "Disable.";
      }
    }
    description
      "";
  }
  typedef devmSplitResumeModeType {
    type enumeration {
      enum "NotSupport" {
        description
          "notsupport.";
      }
      enum "SlaveReset" {
        description
          "slave-reset.";
      }
      enum "FastPreemption" {
        description
          "fast-preemption.";
      }
    }
    description
      "";
  }
  typedef devmMultiChassisType {
    type enumeration {
      enum "ccc" {
        description
          "ccc.";
      }
      enum "clc" {
        description
          "clc.";
      }
    }
    description
      "";
  }
  typedef devmRunModeType {
    type enumeration {
      enum "single" {
        description
          "single.";
      }
      enum "ccc-0" {
        description
          "ccc-0.";
      }
      enum "ccc-1" {
        description
          "ccc-1.";
      }
      enum "ccc-2" {
        description
          "ccc-2.";
      }
      enum "virtual-cluster-chassis" {
        description
          "virtual-cluster-chassis.";
      }
    }
    description
      "";
  }
  typedef devmSetType {
    type enumeration {
      enum "YES" {
        description
          "YES.";
      }
      enum "NO" {
        description
          "NO.";
      }
    }
    description
      "";
  }
  typedef devmSingleInputType {
    type enumeration {
      enum "A" {
        description
          "Single Input Plane A.";
      }
      enum "B" {
        description
          "Single Input Plane B.";
      }
      enum "NA" {
        description
          "Undo Single Input.";
      }
    }
    description
      "information of enum type devmSingleInputType";
  }
}
