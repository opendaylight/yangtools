/*
Copyright (C) 2013-2017 Huawei Technologies Co., Ltd. All rights reserved.
*/
submodule huawei-dns-type {
  belongs-to huawei-dns {
    prefix dns;
  }
  
  organization
    "Huawei Technologies Co.,Ltd.";
  contact
    "Huawei Industrial Base Bantian, Longgang Shenzhen 518129                    
        People's Republic of China                    
        Website: http://www.huawei.com Email: support@huawei.com";
  description
    "Description of submodule dns_type";
  revision 2017-03-23 {
    description
      "Functions supported by the schema are added to the YANG file.";
    reference
      "Huawei private.";
  }
  revision 2013-01-01 {
    description
      "Init revision";
    reference
      "Huawei private.";
  }
  typedef dnsFlag {
    type enumeration {
      enum "false" {
        description
          "NO.";
      }
      enum "true" {
        description
          "YES.";
      }
    }
    description
      "description of dnsFlag";
  }
  typedef dnsQueryType {
    type enumeration {
      enum "standard" {
        description
          "Standard query.";
      }
      enum "inverse" {
        description
          "Inverse query.";
      }
    }
    description
      "description of dnsQueryType";
  }
}
