/*
Copyright (C) 2019-2020 Huawei Technologies Co., Ltd. All rights reserved.
*/
module huawei-mpls-in-udp {
  namespace "urn:huawei:yang:huawei-mpls-in-udp";
  prefix mpls-in-udp;
  import ietf-inet-types {
    prefix inet;
  }
  import huawei-extension {
    prefix ext;
  }
  organization
    "Huawei Technologies Co., Ltd.";
  contact
    "Huawei Industrial Base
     Bantian, Longgang
     Shenzhen 518129
     People's Republic of China
     Website: http://www.huawei.com
     Email: support@huawei.com";
  description
    "Specifies the traffic engineering configuration.";
  revision 2020-03-10 {
    description
      "Fixed some nodes description.";
    reference
      "Huawei private.";
  }
  revision 2019-10-28 {
    description
      "Init revision.";
    reference
      "Huawei private.";
  }
  ext:task-name  "mplsinudp";
  
  container mpls-in-udp {
    presence "Enter mpls-in-udp view.";
    description
      "MPLS in UDP Configuration.";
    container validate-lists {
      description
        "List of source IP address validate.";
      list validate-list {
        key "destination-ip";
        max-elements "2000";
        description
          "Configure source IP address validate.";
        leaf destination-ip {
          type inet:ipv4-address-no-zone;
          description
            "Destination IP address.";
        }
        leaf enable {
          type boolean;
          default "false";
          description
            "Enable/disable validate.";
        }
        container source-ips {
          description
            "List of source IP.";
          list source-ip {
            must "../../destination-ip !=source-ip-address";
            key "source-ip-address";
            max-elements "2000";
            description
              "Configure source IP address.";
            leaf source-ip-address {
              type inet:ipv4-address-no-zone;
              description
                "Source IP address.";
            }
          }
        }
      }
    }
  }
}
