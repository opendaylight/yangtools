/*
Copyright (C) 2013-2017 Huawei Technologies Co., Ltd. All rights reserved.
*/
submodule huawei-ifm-hdlc-type {
  belongs-to huawei-ifm {
    prefix ifm;
  }
  
  organization
    "Huawei Technologies Co.,Ltd.";
  contact
    "Huawei Industrial Base Bantian, Longgang Shenzhen 518129                    
        People's Republic of China                    
        Website: http://www.huawei.com Email: support@huawei.com";
  description
    "hdlc type";
  revision 2017-03-23 {
    description
      "Functions supported by the schema are added to the YANG file.";
    reference
      "Huawei private.";
  }
  revision 2013-01-01 {
    description
      "Init revision";
    reference
      "Huawei private.";
  }

  typedef hdlcDampLevelType {
    type enumeration {
      enum "light" {
        description
          "Light weight";
      }
      enum "middle" {
        description
          "Middle weight";
      }
      enum "heavy" {
        description
          "Heavy weight";
      }
      enum "manual" {
        description
          "Manually configure the parameters";
      }
    }
    description
      "hdlcDampLevelType is light/middle/heavy/manual";
  }
}
