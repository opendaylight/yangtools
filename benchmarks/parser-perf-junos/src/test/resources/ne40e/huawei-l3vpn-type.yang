submodule huawei-l3vpn-type {
  belongs-to huawei-l3vpn {
    prefix l3vpn;
  }

  organization
    "Huawei Technologies Co.,Ltd.";
  contact
    "Huawei Industrial Base Bantian, Longgang Shenzhen 518129                    
        People's Republic of China                    
        Website: http://www.huawei.com Email: support@huawei.com";
  description
    "The type of the l3vpn module.";

  revision 2017-03-23 {
    description
      "Functions supported by the schema are added to the YANG file.";
    reference "Huawei private.";
  }
  revision 2013-01-01 {
    description
      "Init revision";
    reference "Huawei private.";
  }
}
