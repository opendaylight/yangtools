/*
Copyright (C) 2013-2017 Huawei Technologies Co., Ltd. All rights reserved.
*/
submodule huawei-l3vpn-qos-action {
  belongs-to huawei-l3vpn {
    prefix l3vpn;
  }
  include huawei-l3vpn-l3vpncomm;
  include huawei-l3vpn-qos-type;
  include huawei-l3vpn-qos;
  
  organization
    "Huawei Technologies Co.,Ltd.";
  contact
    "Huawei Industrial Base Bantian, Longgang Shenzhen 518129                    
        People's Republic of China                    
        Website: http://www.huawei.com Email: support@huawei.com";
  description
    "the submodule of l3vpn: l3vpn_qos_action";
  revision 2017-03-23 {
    description
      "Functions supported by the schema are added to the YANG file.";
    reference
      "Huawei private.";
  }
  revision 2013-01-01 {
    description
      "Init revision";
    reference
      "Huawei private.";
  }
  rpc qosResetL3vpnPolicyApply {
    description
      "";
    input {
      leaf vrfName {
        type string {
          length "1..31";
        }
        description
          "Name of an l3vpn.";
      }
      leaf vpndirection {
        type qosL3vpnDirectionType;
        description
          "Direction. The available options are inbound and outbound.";
      }
    }
  }
}
