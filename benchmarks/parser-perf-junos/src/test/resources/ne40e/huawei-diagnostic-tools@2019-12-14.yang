/*
Copyright (C) 2019 Huawei Technologies Co., Ltd. All rights reserved.
*/
module huawei-diagnostic-tools {
  yang-version 1;
  namespace "urn:huawei:yang:huawei-diagnostic-tools";
  prefix diagnostic-tools;
  import huawei-extension {
    prefix ext;
  }
  include huawei-diagnostic-tools-ipv4;
  include huawei-diagnostic-tools-ipv6;
  include huawei-diagnostic-tools-lsp;
  include huawei-diagnostic-tools-type;
  include huawei-diagnostic-tools-srv6;
  include huawei-diagnostic-tools-evpn;
  include huawei-diagnostic-tools-common;
  organization
    "Huawei Technologies Co., Ltd.";
  contact
    "Huawei Industrial Base
     Bantian, Longgang
     Shenzhen 518129
     People's Republic of China
     Website: http://www.huawei.com
     Email: support@huawei.com";
  description
     "Diagnosis tool.";

  revision 2019-12-14 {
    description
      "Modify huawei-diagnostic-tools-evpn.";
    reference
      "Huawei private.";
  }

  revision 2019-12-12 {
    description
      "Modify huawei-diagnostic-tools-type.";
    reference
      "Huawei private.";
  }

  revision 2019-12-10 {
    description
      "Modify srv6.";
    reference
      "Huawei private.";
  }
  revision 2019-11-21 {
    description
      "Modify srv6.";
    reference
      "Huawei private.";
  }
  revision 2019-04-12 {
    description
      "Add huawei-diagnostic-tools-evpn.";
    reference
      "Huawei private.";
  }
  revision 2019-04-09 {
    description
      "Init revision.";
    reference
      "Huawei private.";
  }
  ext:task-name "sla";
}
