/*
Copyright (C) 2013-2017 Huawei Technologies Co., Ltd. All rights reserved.
*/
module huawei-isiscomm {
  namespace "http://www.huawei.com/netconf/vrp/huawei-isiscomm";
  prefix isiscomm;
  import huawei-ifm {
    prefix ifm;
  }
  import huawei-l3vpn {
    prefix l3vpn;
  }
  import huawei-pub-type {
    prefix pub-type;
  }
  import ietf-inet-types {
    prefix inet;
  }
  import huawei-extension {
    prefix ext;
  }
  include huawei-isiscomm-action;
  include huawei-isiscomm-type;
  
  organization
    "Huawei Technologies Co.,Ltd.";
  contact
    "Huawei Industrial Base Bantian, Longgang Shenzhen 518129                    
        People's Republic of China                    
        Website: http://www.huawei.com Email: support@huawei.com";
  description
    "IS-IS management.";
  revision 2017-03-23 {
    description
      "Functions supported by the schema are added to the YANG file.";
    reference
      "Huawei private.";
  }
  revision 2013-01-01 {
    description
      "Init revision";
    reference
      "Huawei private.";
  }
  container isiscomm {
    description
      "IS-IS management.";
    container isSites {
      description
        "List of IS-IS instances.";
      list isSite {
        key "instanceId";
        description
          "Set parameters for the IS-IS instance.";
        leaf instanceId {
          type uint32 {
            range "1..4294967295";
          }
          description
            "Set the process ID. If the process ID does not exist, you can create a process. Otherwise, the system fails to create a process. ";
        }
        leaf vpnName {
          type leafref {
            path "/l3vpn:l3vpn/l3vpn:l3vpncomm/l3vpn:l3vpnInstances/l3vpn:l3vpnInstance/l3vpn:vrfName";
          }
          default "_public_";
          description
            "Set the VPN instance name.";
          ext:support-filter "true";
          ext:allowDelete "true";
        }
        leaf isLevel {
          type isiscommLevelType;
          must "((../isLevel='level_1' or ../isLevel='level_2' or ../isLevel='level_1_2') )";
          default "level_1_2";
          description
            "Set the level of a router, which can be level-1, level-2, or level-1-2. The default level is level-1-2.";
        }
        leaf lspMaxAge {
          type uint32 {
            range "2..65535";
          }
          must "(../lspMaxAge>../lspRefreshInterval)";
          default "1200";
          description
            "Set the maximum validity period of the LSP generated by the current IS-IS process. The value is expressed in seconds. The default value is 1200.";
        }
        leaf lspRefreshInterval {
          type uint32 {
            range "1..65534";
          }
          default "900";
          description
            "Set the period for refreshing LSPs. The value is expressed in seconds. The default value is 900.";
        }
        leaf shutDownEnable {
          type boolean;
          default "false";
          description
            "Disable IS-IS.";
        }
        leaf costStyle {
          type isiscommCostStyle;
          default "narrow";
          description
            "Set the cost type for the IS-IS router to receive and send routes. The available options are Narrow, Wide, Wide-compatible, Compatible, and Narrow-compatible.";
        }
        leaf relaxSpfLimit {
          type boolean;
          must "(../costStyle!='transition' and ../costStyle!='ntransition' and ../relaxSpfLimit='false') or (../costStyle='transition' or ../costStyle='ntransition')";
          default "false";
          description
            "Allow the device to receive the routes with a cost greater than 1023.";
        }
        leaf linkQuaDeteEn {
          type boolean;
          default "false";
          description
            "Enable Link Quality Detection";
        }
        leaf spfMaxInterval {
          type uint32 {
            range "1..120";
          }
          default "5";
          description
            "Set the maximum delay time for route calculation. The value is an integer, expressed in seconds. The default value is 5.";
        }
        leaf spfInitInterval {
          type uint32 {
            range "0..60000";
          }
          must "(../spfInitInterval<../spfMaxInterval*1000)";
          default "50";
          description
            "Set the delay for the first route calculation. The value is an integer, expressed in milliseconds. The default value is 50.";
        }
        leaf spfIncrInterval {
          type uint32 {
            range "0..60000";
          }
          must "(../spfIncrInterval<../spfMaxInterval*1000)";
          default "200";
          description
            "Set the incremental delay between two route calculations. The delay doubles the previous one each time. The value is an integer, expressed in milliseconds. The default value is 200.";
        }
        leaf level1lspLengthOrig {
          type uint32 {
            range "512..16384";
          }
          must "(../level1lspLengthOrig<=../lspReceiveLength) and ((../level1lspLengthOrig=../level2lspLengthOrig))";
          default "1497";
          description
            "Set the maximum size of the level-1 LSPs that are generated locally. The value is expressed in bytes. The default value is 1497.";
        }
        leaf level2lspLengthOrig {
          type uint32 {
            range "512..16384";
          }
          must "(../level2lspLengthOrig<=../lspReceiveLength)";
          default "1497";
          description
            "Set the maximum size of the level-2 LSPs that are generated locally. The value is expressed in bytes. The default value is 1497.";
        }
        leaf lspReceiveLength {
          type uint32 {
            range "512..16384";
          }
          default "1497";
          description
            "Set the maximum size of the LSPs that can be received. The value is expressed in bytes. The default value is 1497.";
        }
        leaf level1LspFragExtEnable {
          type boolean;
          default "false";
          description
            "Enable the level-1 LSP fragment extension.";
        }
        leaf level2LspFragExtEnable {
          type boolean;
          default "false";
          description
            "Enable the level-2 LSP fragment extension.";
        }
        leaf level1LspFragExtMode {
          when "../level1LspFragExtEnable='true'";
          type isiscommLspFragMode;
          must "not(../level1LspFragExtEnable='true' and ../level2LspFragExtEnable='true') or (../level1LspFragExtEnable='true' and ../level2LspFragExtEnable='true' and ../level1LspFragExtMode=../level2LspFragExtMode)";
          default "mode_1";
          description
            "Mode in which the level-1 LSP fragments extension is enabled. The mode can be mode-1 or mode-2. The default mode is mode-1.";
        }
        leaf level2LspFragExtMode {
          when "../level2LspFragExtEnable='true'";
          type isiscommLspFragMode;
          default "mode_1";
          description
            "Mode in which the level-2 LSP fragments extension is enabled. The mode can be mode-1 or mode-2. The default mode is mode-1.";
        }
        leaf localSymbolicName {
          type string {
            length "0..64";
          }
          description
            "Set a dynamic host name for the local system.";
          ext:allowDelete "true";
        }
        leaf stdAutoCostEnable {
          type boolean;
          default "false";
          description
            "Enable automatic cost calculation for the system. By default, the function is disabled.";
        }
        leaf stdAutoCostEnableCompatible {
          when "../stdAutoCostEnable='true'";
          type boolean;
          default "false";
          description
            "Enable automatic cost calculation compatibly for the system. By default, the function is disabled.";
        }
        leaf stdbandwidth {
          type uint32 {
            range "1..2147483648";
          }
          default "100";
          description
            "Set a bandwidth reference used for the automatic calculation of the cost for an interface. The value is expressed in Mbit/s. The default value is 100.";
        }
        leaf stdLevel1Cost {
          type uint32 {
            range "1..16777215";
          }
          must "(../costStyle!='wide' and ../costStyle!='wtransition' and ../stdLevel1Cost>=1) and ((../costStyle!='wide' and ../costStyle!='wtransition' and ../stdLevel1Cost<=63)) or ((not(../costStyle!='wide' and ../costStyle!='wtransition') and ../stdLevel1Cost>=1) and ((not(../costStyle!='wide' and ../costStyle!='wtransition') and ../stdLevel1Cost<=16777215)))";
          description
            "Set a level-1 interface cost. If the IS-IS cost type is narrow, narrow-compatible, or compatible, the value ranges from 1 to 63. If the IS-IS cost type is wide or wide-compatible, the value ranges from 1 to 16777215.";
          ext:allowDelete "true";
        }
        leaf stdLevel2Cost {
          type uint32 {
            range "1..16777215";
          }
          must "(../costStyle!='wide' and ../costStyle!='wtransition' and ../stdLevel2Cost>=1) and ((../costStyle!='wide' and ../costStyle!='wtransition' and ../stdLevel2Cost<=63)) or ((not(../costStyle!='wide' and ../costStyle!='wtransition') and ../stdLevel2Cost>=1) and ((not(../costStyle!='wide' and ../costStyle!='wtransition') and ../stdLevel2Cost<=16777215)))";
          description
            "Set a level-2 interface cost. If the IS-IS cost type is narrow, narrow-compatible, or compatible, the value ranges from 1 to 63. If the IS-IS cost type is wide or wide-compatible, the value ranges from 1 to 16777215.";
          ext:allowDelete "true";
        }
        leaf baseTopoType {
          type isiscommBaseTopoType;
          default "invalid";
          description
            "Type of IPv6 enabling, which can be Standard, Compatible, IPv6, or Compatible IPv6 SPF.";
        }
        leaf ldpAutoCfg {
          when "not(../vpnName!='_public_' and ../vpnName)";
          type boolean;
          default "false";
          description
            "Auto MPLS LDP configuration on an interface.";
        }
        leaf poiEnable {
          type boolean;
          default "false";
          description
            "Enable purge-originator-identification.";
        }
        leaf poiAlways {
          type boolean;
          must "not(../poiEnable='false') or (../poiEnable='false' and ../poiAlways='false')";
          default "false";
          description
            "Set purge-originator-identification always with POI TLV.";
        }
        leaf lsdbLimit {
          type boolean;
          default "false";
          description
            "Limit the number of the LSDBs.";
        }
        leaf lsdbLimitNum {
          when "../lsdbLimit='true'";
          type uint32 {
            range "1..100000";
          }
          default "100000";
          description
            "Maximum number of LSDBs.";
        }
        leaf lsdbThresUpper {
          when "../lsdbLimit='true'";
          type uint8 {
            range "1..100";
          }
          default "80";
          description
            "Threshold upper percentage of the maximum number of LSDBs, used to trigger an alarm.";
        }
        leaf lsdbThresLower {
          when "../lsdbLimit='true'";
          type uint8 {
            range "1..100";
          }
          default "70";
          description
            "Threshold lower percentage of the maximum number of LSDBs, used to trigger a clear alarm.";
        }
        leaf directInherit {
          type boolean;
          default "false";
          description
            "Inherit the Direct Route Property.";
        }
        leaf description {
          type string {
            length "0..80";
            pattern '([^?]*)';
          }
          description
            "Set a description information text. The value is a string of case-sensitive characters. ";
        }
        leaf peerFlappingSuppress {
          type boolean;
          default "true";
          description
            "Enable the neighbor relationship flapping suppression function. By default, the function is enabled.";
        }
        leaf isSREnableMPLS {
          type boolean;
          default "false";
          description
            "Enable SegmentRouting MPLS.";
        }
        container isLspAgeRefresh {
          description
            "Refresh the remaining-lifetime field of a LSP.";
          leaf isLspAgeRefreshEnable {
            type boolean;
            default "true";
            description
              "Enable refresh remaining-lifetime field. By default, the feature is disabled.";
            ext:allowDelete "false";
          }
          leaf lspAgeRefreshMaxAge {
            when "not(../isLspAgeRefreshEnable='false')";
            type boolean;
            default "true";
            description
              "Use max-age as remaining-lifetime refresh value.";
            ext:allowDelete "false";
          }
          leaf lspAgeRefreshValue {
            when "not(../isLspAgeRefreshEnable='false') or ../isLspAgeRefreshEnable='true' and ../lspAgeRefreshMaxAge='false'";
            type uint16 {
              range "2..65535";
            }
            default "1200";
            description
              "Set remaining-lifetime refresh value.";
            ext:allowDelete "false";
          }
        }
        container isBgpLs {
          when "not(../vpnName!='_public_' and ../vpnName)";
          description
            "Enable the Bgp-ls.";
          leaf l1BgpLsEnable {
            type boolean;
            must "((../../isExternAbility/vClusterEnable='false' and ../../isExternAbility/vAccessEnable='false' and ../l1BgpLsEnable='true') or ../l1BgpLsEnable='false')";
            default "false";
            description
              "Enable Level 1 bgp-ls.";
            ext:allowDelete "false";
          }
          leaf l2BgpLsEnable {
            type boolean;
            must "((../../isExternAbility/vClusterEnable='false' and ../../isExternAbility/vAccessEnable='false' and ../l2BgpLsEnable='true') or ../l2BgpLsEnable='false')";
            default "false";
            description
              "Enable Level 2 bgp-ls.";
            ext:allowDelete "false";
          }
          leaf identifier {
            when "not(../l1BgpLsEnable='false' and ../l2BgpLsEnable='false')";
            type uint32 {
              range "2..65535";
            }
            description
              "Set bgp-ls identifier.";
            ext:allowDelete "true";
          }
        }
        container isLspGenIntelliTimer {
          description
            "Set an intelligent timer to generate LSPs.";
          leaf level1LspGenMaxInterval {
            type uint32 {
              range "1..120";
            }
            default "2";
            description
              "Set the maximum delay for generating level-1 LSPs with the same LSP ID. The value is an integer, expressed in seconds. The default value is 2.";
          }
          leaf level2LspGenMaxInterval {
            type uint32 {
              range "1..120";
            }
            default "2";
            description
              "Set the maximum delay for generating level-2 LSPs with the same LSP ID. The value is an integer, expressed in seconds. The default value is 2.";
          }
          leaf level1LspGenInitInterval {
            type uint32 {
              range "0..60000";
            }
            must "(../level1LspGenInitInterval<../level1LspGenMaxInterval*1000)";
            default "0";
            description
              "Set the delay for generating level-1 LSPs with the same LSP ID for the first time. The value is an integer, expressed in milliseconds. By default, this delay is not used.";
          }
          leaf level2LspGenInitInterval {
            type uint32 {
              range "0..60000";
            }
            must "(../level2LspGenInitInterval<../level2LspGenMaxInterval*1000)";
            default "0";
            description
              "Set the delay for generating level-2 LSPs with the same LSP ID for the first time. The value is an integer, expressed in milliseconds. By default, this delay is not used.";
          }
          leaf level1LspGenIncrInterval {
            type uint32 {
              range "0..60000";
            }
            must "(../level1LspGenIncrInterval<../level1LspGenMaxInterval*1000)";
            default "0";
            description
              "Set the incremental delay for generating two level-1 LSPs with the same LSP ID. The interval doubles the previous one each time. The value is an integer, expressed in milliseconds. By default, the delay is not used.";
          }
          leaf level2LspGenIncrInterval {
            type uint32 {
              range "0..60000";
            }
            must "(../level2LspGenIncrInterval<../level2LspGenMaxInterval*1000)";
            default "0";
            description
              "Set the incremental delay for generating two level-2 LSPs with the same LSP ID. The interval doubles the previous one each time. The value is an integer, expressed in milliseconds. By default, the delay is not used.";
          }
        }
        container isFlashFlood {
          description
            "Enable immediate LSP flooding.";
          leaf level1FlashFloodEnable {
            type boolean;
            default "false";
            description
              "Enable level-1 LSP flooding.";
          }
          leaf level2FlashFloodEnable {
            type boolean;
            default "false";
            description
              "Enable level-2 LSP flooding.";
          }
          leaf level1FlashFloodLspNum {
            when "../level1FlashFloodEnable='true'";
            type uint32 {
              range "1..15";
            }
            default "5";
            description
              "Set the maximum number of level-1 LSPs that can be flooded each time on each interface. The default value is 5. ";
          }
          leaf level2FlashFloodLspNum {
            when "../level2FlashFloodEnable='true'";
            type uint32 {
              range "1..15";
            }
            default "5";
            description
              "Set the maximum number of level-2 LSPs that can be flooded each time on each interface. The default value is 5. ";
          }
          leaf level1FlashFloodMaxTime {
            when "../level1FlashFloodEnable='true'";
            type uint32 {
              range "10..50000";
            }
            default "10";
            description
              "Set the maximum interval at which level-1 LSPs are flooded. The value is expressed in milliseconds. The default value is 10.";
          }
          leaf level2FlashFloodMaxTime {
            when "../level2FlashFloodEnable='true'";
            type uint32 {
              range "10..50000";
            }
            default "10";
            description
              "Set the maximum interval at which level-2 LSPs are flooded. The value is expressed in milliseconds. The default value is 10.";
          }
        }
        container isOverloadSet {
          description
            "Set overload.";
          leaf stdOverloadType {
            type isiscommIsOverLoadType;
            default "no_set";
            description
              "Set the router to notify others that it is overloaded. The flag can be No Setting, Restart Setting, or Manual Setting. The default value is No Setting.";
          }
          leaf stdOverloadWaitType {
            when "../stdOverloadType='on_startup'";
            type isiscommWaitType;
            default "no_wait";
            description
              "Set the overload type. The value can be Wait for BGP Convergence, Wait for Neighbor, or Not Wait. The default value is Not Wait.";
          }
          leaf stdOverloadNbrSysId {
            when "../stdOverloadWaitType='start_from_nbr'";
            type string {
              length "1..15";
              pattern '((([0-9]|[a-f]|[A-F]){4}\.){2}([0-9]|[a-f]|[A-F]){4})';
            }
            description
              "Set the system ID of the neighbor. The duration for the system to keep the overload bit is set according to the status of the neighbor specified by the system ID. The length of the value is 6 bytes, in the format of XXXX.XXXX.XXXX, in which X is a hexadecimal case-insensitive character. ";
            ext:allowDelete "true";
          }
          leaf stdOverloadTimeout1 {
            when "../stdOverloadWaitType='start_from_nbr'";
            type uint32 {
              range "5..86400";
            }
            default "1200";
            description
              "If the specified neighbor does not become Up before the neighbor holdtime expires, the holdtime of the system overload flag is the neighbor holdtime. The value of neighbor holdtime is expressed in seconds, ranging from 5 to 86400. The default value is 1200. ";
          }
          leaf stdOverloadTimeout2 {
            when "../stdOverloadType='on_startup'";
            type uint32 {
              range "5..86400";
            }
            default "600";
            description
              "If the specified neighbor becomes Up before the neighbor holdtime expires, the system overload flag keeps the neighbor timeout period. The neighbor timeout period is expressed in seconds, ranging from 5 to 86400. The default value is 600.";
          }
          leaf stdOverloadInterlevel {
            when "not(../stdOverloadType='no_set')";
            type boolean;
            default "false";
            description
              "Determine whether a device can advertise the IP address prefixes learned from the IS-IS routes at different levels. By default, such IP address prefixes cannot be advertised.";
          }
          leaf stdOverloadExternal {
            when "not(../stdOverloadType='no_set')";
            type boolean;
            default "false";
            description
              "Determine whether a device can advertise the IP address prefixes learned from other protocols. By default, such IP address prefixes cannot be advertised.";
          }
          leaf stdOverloadSendSaBit {
            when "not(../stdOverloadType='no_set') or ../stdOverloadType='on_startup'";
            type boolean;
            default "false";
            description
              "Set the SA bit in Hello packets.";
          }
          leaf stdOverloadSaBitTime {
            when "not(../stdOverloadType='no_set') or ../stdOverloadSendSaBit='true'";
            type uint32 {
              range "5..120";
            }
            default "30";
            description
              "The SA bit advertisement period is carried in Hello packet. The value is expressed in seconds, The default value is 30 seconds.";
          }
        }
        container isLdpSyncdSet {
          description
            "Set LDP and IS-IS synchronization.";
          leaf ldpSyncEnable {
            type boolean;
            default "false";
            description
              "Enable LDP and IS-IS synchronization on an interface. By default, LDP and IS-IS synchronization is disabled.";
          }
          leaf ldpSyncBind {
            when "../ldpSyncEnable='true'";
            type boolean;
            default "false";
            description
              "Enable MPLS LDP association. By default, MPLS LDP association is disabled.";
          }
          leaf ldpSyncTimerEnable {
            type boolean;
            default "false";
            description
              "Enable the LDP and IS-IS synchronization timer. By default, the LDP and IS-IS synchronization timer is disabled.";
          }
          leaf ldpSyncTimer {
            when "../ldpSyncTimerEnable='true'";
            type uint32 {
              range "0..65535";
            }
            default "0";
            description
              "Set a value for the LDP and IS-IS synchronization timer. The value is expressed in seconds. ";
          }
          leaf ldpSyncHDTimerEnable {
            type boolean;
            default "false";
            description
              "Enable the LDP and IS-IS synchronization holddown timer. By default, the LDP and IS-IS synchronization holddown timer is disabled.";
          }
          leaf ldpSyncHDTimer {
            when "../ldpSyncHDTimerEnable='true'";
            type uint32 {
              range "0..65535";
            }
            default "0";
            description
              "Set a value for the LDP and IS-IS synchronization holddown timer. The value is expressed in seconds. ";
          }
        }
        container isExternAbility {
          description
            "Expansibility.";
          leaf adjStrictCheck {
            type boolean;
            default "false";
            description
              "Strict check on the neighbor.";
          }
          leaf ecmpPrefer {
            type isiscommEcmpPreferType;
            must "((../ecmpPrefer='none' or ../ecmpPrefer='teTunnel' or ../ecmpPrefer='intact') )";
            default "none";
            description
              "Configure whether the routes with a TE tunnel interface as the outbound interface or the routes with an IPv4 interface as the outbound interface are preferentially selected to load-balance IS-IS traffic.";
          }
          leaf optChecksum {
            type boolean;
            default "false";
            description
              "Option Checksum.";
          }
          leaf attAdvControl {
            type isiscommAttAdvMode;
            default "noType";
            description
              "Control to advertise the ATT bit.";
          }
          leaf attAvoidLearn {
            type boolean;
            default "false";
            description
              "Prevent the device from learning the LSPs with the ATT bit.";
          }
          leaf vClusterEnable {
            type boolean;
            must "((../../isBgpLs/l1BgpLsEnable='false' and ../../isBgpLs/l2BgpLsEnable='false' and ../vClusterEnable='true' and ../vAccessEnable='false') or ../vClusterEnable='false')";
            default "false";
            description
              "Enable virtual cluster on the system.";
          }
          leaf vAccessEnable {
            type boolean;
            must "((../../isBgpLs/l1BgpLsEnable='false' and ../../isBgpLs/l2BgpLsEnable='false' and ../vClusterEnable='false' and ../vAccessEnable='true') or ../vAccessEnable='false')";
            default "false";          
            description
              "Enable virtual access on the system.";
          }
        }
        container isLocalMtSets {
          description
            "List of local multicast topologies.";
          container isLocalMtSet {
            description
              "Set a local multicast topology.";
            leaf localMtEnable {
              type boolean;
              default "false";
              description
                "Enable local multicast topology.";
            }
            leaf policyType {
              when "not(../localMtEnable='false')";
              type isiscommIsPolicyType;
              must "../localMtEnable='false' or (not(../localMtEnable='false') and (../policyType='noType' or ../policyType='aclNumOrName' or ../policyType='ipPrefix') )";
              description
                "Set a policy mode for route filtering. In ACL mode, the ACL number parameter is available. In IP prefix mode, the IP prefix parameter is available. In None mode, both the ACL number and IP prefix parameters are unavailable.";
            }
            leaf aclNumOrName {
              when "../policyType='aclNumOrName'";
              type string {
                length "1..64";
                pattern '\s*(2[0-9]{3}|[a-zA-Z]\S*)\s*';
              }
              description
                "Set the ACL number or name used for route filtering. The ACL number ranges from 2000 to 2999. The ACL name must start with a letter, and the ACL name is case-sensitive.";
              ext:allowDelete "true";
            }
            leaf ipPrefix {
              when "../policyType='ipPrefix'";
              type string {
                length "1..169";
                pattern '.*\S.*';
              }
              description
                "IP prefix name used during route filtering. ";
              ext:allowDelete "true";
            }
          }
        }
        container isAreaIds {
          description
            "Auto list of NETs. ";
          list isAreaId {
            key "areaId autoSysIdStyle";
            max-elements  "3";
            description
              "Set an Auto NET.";
            leaf areaId {
              type string {
                length "0..53";
                pattern '49.0001|^\s*((([0-9a-fA-F]\.?){2}){1,13})\s*$';
              }
              description
                "Set an area ID. The area ID is in the format of XX.XXXX.XXXX...XXXX, in which X is a case-insensitive hexadecimal character. A maximum of 13 Xs are allowed.";
            }
            leaf autoSysIdStyle {
              type isiscommAutoSysIdType;
              description
                "Set automatic system ID mapping.";
            }
          }
        }
        container isNetEntitys {
          description
            "List of NETs. ";
          list isNetEntity {
            key "netEntity";
            max-elements  "3";
            description
              "Set a NET.";
            leaf netEntity {
              type string {
                length "0..83";
                pattern '\s*((([0-9a-fA-F]\.?){2}){7,19}0\.?0)\s*';
              }
              description
                "Set a NET. The NET is in the format of X...X.XXXX.XXXX.XXXX.00, in which X...X indicates the area address, the 12 Xs in the middle indicate the system ID, and the last 00 indicates the SEL. X is a case-insensitive hexadecimal character. Manual configuration and automatic configuration are mutually exclusive on PTN devices. The NET cannot be manually configured when creating a process.";
            }
          }
        }
        container isLspAuthtications {
          description
            "Routing packet authentication list.";
          list isLspAuthtication {
            key "cmdType";
            max-elements  "2";
            description
              "Authenticate received routing packets (LSPs or SNPs) based on the specified authentication mode and password in an IS-IS area or domain. ";
            leaf cmdType {
              type isiscommAuthCmdType;
              description
                "Set the command type, which can be area or domain.";
            }
            leaf passwordType {
              type isiscommAuthType;
              mandatory true;
              description
                "Set the authentication type, which can be simple or MD5.";
            }
            leaf simplePassword {
              when "not(../passwordType='hmac_sha256' or ../passwordType='keychain' or ../passwordType='md5') or ../passwordType='simple'";
              type pub-type:password {
                length "1..16";
              }
              description
                "Set a plaintext for the simple authentication. The value is a string of characters (letters or digits), spaces not supported.";
              ext:allowDelete "true";
            }
            leaf md5Password {
              when "not(../passwordType='keychain' or ../passwordType='simple') or ../passwordType='hmac_sha256' or ../passwordType='md5'";
              type pub-type:passwordExtend {
                length "1..255";
              }
              description
                "Set a MD5 or HMAC-SHA256 authentication password. The value is a string of characters (letters or digits), spaces not supported.";
              ext:allowDelete "true";
            }
            leaf serviceType {
              when "not(../passwordType='hmac_sha256' or ../passwordType='keychain') or ../passwordType='md5' or ../passwordType='simple'";
              type isiscommIsServiceType;
              default "osi";
              description
                "Set the authentication service type, which can be IP or OSI.";
            }
            leaf authenUsage {
              type isiscommAuthUsageType;
              default "usage_default";
              description
                "Set the authentication mode. The available options are as follows: 
authentication-avoid: In this mode, the authentication information is not encapsulated for the generated SNPs, and the received SNPs are not checked. The authentication information is encapsulated for only the generated LSPs, and the received LSPs are checked.
send-only: In this mode, the authentication information is encapsulated for the generated LSPs and SNPs. Only the received LSPs are checked.
all-send-only: In this mode, the authentication information is encapsulated for the generated LSPs and SNPS. The received LSPs and SNPs, however, are not checked.";
            }
            leaf keyId {
              when "../passwordType='hmac_sha256'";
              type uint16 {
                range "0..65535";
              }
              default "0";
              description
                "Set a value for key ID.";
              ext:allowDelete "true";
            }
          }
        }
        container isNameTables {
          description
            "List of name mapping information.";
          list isNameTable {
            key "systemId";
            max-elements  "500";
            description
              "Enable the ability to identify the host names in LSPs. On the local end, a mapping name (an alias) is configured for the IS-IS system on the remote end. The mapping name is not advertised.";
            leaf systemId {
              type string {
                length "12..31";
                pattern '((([0-9]|[a-f]|[A-F]){4}\.){2}([0-9]|[a-f]|[A-F]){4}(\.([0-9]|[a-f]|[A-F]){2})?)';
              }
              description
                "ID of the IS-IS system on the remote end or the pseudo node ID. The value is in the format of XXXX.XXXX.XXXX[.XX], in which X is a case-insensitive hexadecimal character. The value of a pseudo node cannot be 0.";
            }
            leaf hostName {
              type string {
                length "1..64";
                pattern '.*\S.*';
              }
              mandatory true;
              description
                "Name of the IS-IS system on the remote end. ";
            }
          }
        }
        container isVirtualSystems {
          description
            "Virtual system list.";
          list isVirtualSystem {
            key "virtualSystemId";
            max-elements  "99";
            description
              "Virtual system ID used to set the IS-IS process. Without a system ID, extended LSPs are not generated. ";
            leaf virtualSystemId {
              type string {
                length "12..19";
                pattern '((([0-9]|[a-f]|[A-F]){4}\.){2}([0-9]|[a-f]|[A-F]){4})';
              }
              description
                "Set a virtual system ID for an IS-IS process. The length of the value is 6 bytes. The value is in the format of XXXX.XXXX.XXXX, in which X is a case-insensitive hexadecimal character.";
            }
          }
        }
        container isSrgbs {
          description
            "List of Segment Routing Global-block.";
          list isSrgb {
            key "srgbBegin srgbEnd";
            description
              "Information about Segment Routing Global-block.";
            leaf srgbBegin {
              type uint32 {
                range "0..1048575";
              }
              description
                "SRGB begin value.";
              ext:allowDelete "false";
            }
            leaf srgbEnd {
              type uint32 {
                range "0..1048575";
              }
              description
                "SRGB end value.";
              ext:allowDelete "false";
            }
          }
        }
        container isCircuits {
          description
            "List of IS-IS interfaces.";
          list isCircuit {
            key "ifName";
            description
              "Set parameters for an IS-IS interface.";
            leaf ifName {
              type leafref {
                path "/ifm:ifm/ifm:interfaces/ifm:interface/ifm:ifName";
              }
              must "(../ipv4Enable = 'true') or (../ipv6Enable = 'true')";
              description
                "Interface name.";
            }
            leaf ipv4Enable {
              type boolean;
              default "true";
              description
                "Enable IS-IS IPv4 on an interface. This flag or the flag for enabling IS-IS IPv6 must be enabled when creating an interface and at least one needs to be true during the modification of an interface.";
            }
            leaf ipv6Enable {
              type boolean;
              must "not(../../../baseTopoType='invalid') and (not(../ipv4Enable='false') or (../ipv4Enable='false' and ../ipv6Enable!='false'))";
              default "false";
              description
                "Enable IS-IS IPv6 on an interface. IPv6 must have been enabled in a process and on the interface. This flag or the flag for enabling IS-IS IPv4 must be enabled when creating an interface and at least one needs to be true during the modification of an interface.";
            }
            leaf circuitLevelType {
              type isiscommLevelType;
              must "((../circuitLevelType='level_1' or ../circuitLevelType='level_2' or ../circuitLevelType='level_1_2') )";
              default "level_1_2";
              description
                "Set a level for an interface, which can be level-1, level-2, or level-1-2. The default value is level-1-2.";
            }
            leaf typeP2pEnable {
              type boolean;
              default "false";
              description
                "Emulate an interface as a P2P interface. This command takes effect only when the interface is of the broadcast type.";
            }
            leaf snpaCheck {
              type boolean;
              default "false";
              description
                "Enable the SNPA check of LSP and SNP.";
            }
            leaf silentEnable {
              type boolean;
              default "false";
              description
                "Prevent an interface from receiving and sending IS-IS packets. By default, an interface can receive and send IS-IS packets. ";
            }
            leaf silentCost {
              when "../silentEnable='true'";
              type boolean;
              default "false";
              description
                "Advertise the silent cost.";
            }
            leaf level1CsnpInterval {
              type uint32 {
                range "1..65535";
              }
              default "10";
              description
                "Set the interval at which level-1 CSNPs are sent. The value is expressed in seconds. The default value is 10.";
            }
            leaf level2CsnpInterval {
              type uint32 {
                range "1..65535";
              }
              default "10";
              description
                "Set the interval at which level-2 CSNPs are sent. The value is expressed in seconds. The default value is 10.";
            }
            leaf throttleTimer {
              type uint32 {
                range "1..10000";
              }
              default "50";
              description
                "Set the minimum interval at which LSPs are sent. The value is expressed in milliseconds. The default value is 50.";
            }
            leaf throttleCount {
              type uint32 {
                range "1..1000";
              }
              default "10";
              description
                "Set the maximum number of LSPs that are sent during the interval. The value is expressed in milliseconds. The default value is 10.";
            }
            leaf level1HelloTimer {
              type uint32 {
                range "3..255";
              }
              default "10";
              description
                "Set the interval at which level-1 Hello packets are sent. The value is expressed in seconds. The default value is 10.";
            }
            leaf level2HelloTimer {
              type uint32 {
                range "3..255";
              }
              default "10";
              description
                "To set the interval for sending level-2 Hello packets. The value is expressed in seconds. The default value is 10.";
            }
            leaf level1HoldMultiplier {
              type uint32 {
                range "3..1000";
              }
              default "3";
              description
                "Set the number of Hello packets that the local IS-IS router fails to receive from a level-1 neighbor before the local router declares the neighbor Down. The default value is 3.";
            }
            leaf level2HoldMultiplier {
              type uint32 {
                range "3..1000";
              }
              default "3";
              description
                "Set the number of Hello packets that the local IS-IS router fails to receive from a level-2 neighbor before the local router declares the neighbor Down. The default value is 3.";
            }
            leaf disName {
              type string {
                length "0..64";
                pattern '.*\S.*';
              }
              description
                "Set a name for the DIS on the LAN.";
              ext:allowDelete "true";
            }
            leaf level1DisPriority {
              type uint32 {
                range "0..127";
              }
              default "64";
              description
                "Set a priority for level-1 DIS election. The default value is 64. The greater the value, the higher the priority.";
            }
            leaf level2DisPriority {
              type uint32 {
                range "0..127";
              }
              default "64";
              description
                "Set a priority for level-2 DIS election. The default value is 64. The greater the value, the higher the priority.";
            }
            leaf p2pPeerIPIgnore {
              type boolean;
              default "false";
              description
                "Ignore the IP address check when P2P Hello packets are received. By default, the IP addresses are checked when P2P Hello packets are received.";
            }
            leaf p2pNegotiationMode {
              type isiscommP2pNegotiation;
              default "3_way";
              description
                "Set the P2P neighbor negotiation type, which can be 2-way, 3-way, or 3-way only. The default value is 3-way.";
            }
            leaf p2pHelloTimer {
              type uint32 {
                range "3..255";
              }
              default "10";
              description
                "Set the interval at which P2P Hello packets are sent. The value is expressed in seconds. The default value is 10.";
            }
            leaf p2pHoldMulti {
              type uint32 {
                range "3..1000";
              }
              default "3";
              description
                "Set the number of P2P Hello packets that the local IS-IS router fails to receive from a P2P neighbor before the local router declares the neighbor Down. The default value is 3.";
            }
            leaf lspRetransmitInterval {
              type uint32 {
                range "1..300";
              }
              default "5";
              description
                "Set the interval for retransmitting LSPs on the P2P link. The value is expressed in seconds. The default value is 5.";
            }
            leaf pPPOsicpCheckEnable {
              type boolean;
              default "false";
              description
                "Check the OSICP negotiation status on the interfaces with PPP link protocols. The negotiation status affects the status of the interfaces in IS-IS. By default,  the OSICP negotiation status is not checked.";
            }
            leaf ldpAutoBlock {
              type boolean;
              must "(../../../vpnName!='_public_' and ../ldpAutoBlock='false') or (../../../vpnName='_public_')";
              default "false";
              description
                "Disable automatic MPLS LDP configuration on an interface.";
            }
            leaf helloMode {
              type isiscommPadType;
              default "normal";
              description
                "Set the Hello packet padding type, which can be Small, Padding, or Normal. The default value is Normal.";
            }
            leaf level1Cost {
              type uint32 {
                range "0..16777215";
              }
              must "(../../../costStyle!='wide' and ../../../costStyle!='wtransition' and ../level1Cost<=63) or ((not(../../../costStyle!='wide' and ../../../costStyle!='wtransition') and ../level1Cost<=16777215))";
              description
                "Link cost of an interface used for the level-1 SPF calculation. If the IS-IS cost type is narrow, narrow-compatible, or compatible, the value ranges from 1 to 63. If the IS-IS cost type is wide or wide-compatible, the value ranges from 1 to 16777215.The interface of LoopBack can use the value of 0.";
              ext:allowDelete "true";
            }
            leaf level2Cost {
              type uint32 {
                range "0..16777215";
              }
              must "(../../../costStyle!='wide' and ../../../costStyle!='wtransition' and ../level2Cost<=63) or ((not(../../../costStyle!='wide' and ../../../costStyle!='wtransition') and ../level2Cost<=16777215))";
              description
                "Link cost of an interface used for the level-2 SPF calculation. If the IS-IS cost type is narrow, narrow-compatible, or compatible, the value ranges from 1 to 63. If the IS-IS cost type is wide or wide-compatible, the value ranges from 1 to 16777215.The interface of LoopBack can use the value of 0.";
              ext:allowDelete "true";
            }
            leaf ldpSyncState {
              type isiscommLdpSyncState;
              default "noConfig";
              description
                "LDP and IS-IS synchronization state on an interface, which can be NoConfig, Enable, or Block. The default value is NoConfig.";
            }
            leaf ldpSyncTimerEnable {
              type boolean;
              default "false";
              description
                "Enable the LDP and IS-IS synchronization timer.";
            }
            leaf ldpSyncTimer {
              when "../ldpSyncTimerEnable='true'";
              type uint32 {
                range "0..65535";
              }
              default "0";
              description
                "Set a value for the LDP and IS-IS synchronization timer. The value is expressed in seconds.";
            }
            leaf ldpSyncHDTimerEnable {
              type boolean;
              default "false";
              description
                "Enable the LDP and IS-IS synchronization holddown timer. ";
            }
            leaf ldpSyncHDTimer {
              when "../ldpSyncHDTimerEnable='true'";
              type uint32 {
                range "0..65535";
              }
              default "0";
              description
                "Set a value for the LDP and IS-IS synchronization holddown timer. The value is expressed in seconds. ";
            }
            leaf ldpSynInfinite {
              type boolean;
              default "false";
              description
                "Enable infinite LDP and IS-IS synchronization. The LDP and IS-IS synchronization is kept before the LDP session goes Up.";
            }
            leaf level1FrrBlock {
              type boolean;
              default "false";
              description
                "Prevent an interface from participating Level-1 LFA Backup Interface calculation in an IPv4 base topology.";
            }
            leaf level2FrrBlock {
              type boolean;
              default "false";
              description
                "Prevent an interface from participating Level-2 LFA Backup Interface calculation in an IPv4 base topology.";
            }
            leaf level1RemoteLFA {
              type boolean;
              default "false";
              description
                "Disable Level-1 RLFA of the Interface.";
            }
            leaf level2RemoteLFA {
              type boolean;
              default "false";
              description
                "Disable Level-2 RLFA of the Interface.";
            }
            leaf l1TilfaDisable {
              type boolean;
              default "false";
              description
                "Whether an interface is prevented from being calculated as a valid backup interface during Level-1 LFA calculation in the IPv4 base topology.";
            }
            leaf l2TilfaDisable {
              type boolean;
              default "false";
              description
                "Whether an interface is prevented from being calculated as a valid backup interface during Level-2 LFA calculation in the IPv4 base topology.";
            }
            leaf peerFlapSuppressEnable {
              type boolean;
              default "true";
              description
                "Enable the neighbor relationship flapping suppression function. By default, the function is enabled.";
              ext:allowDelete "false";
            }
            leaf peerFlapSuppressDetectInterval {
              type uint32 {
                range "1..300";
              }
              default "60";
              description
                "Set the detection interval of neighbor relationship flapping suppression, in seconds. If the neighbor relationship goes Down twice within the interval, a flapping event is recorded. The default value is 60. ";
              ext:allowDelete "false";
            }
            leaf peerFlapSuppressThreshold {
              type uint32 {
                range "1..1000";
              }
              default "10";
              description
                "Set the threshold of IS-IS neighbor relationship flapping suppression. When the flapping_count reaches or exceeds the threshold, flapping suppression takes effect. The default value is 10.";
              ext:allowDelete "false";
            }
            leaf peerFlapSuppressResumeInterval {
              type uint32 {
                range "2..1000";
              }
              default "120";
              description
                "Set the interval for exiting from IS-IS neighbor relationship flapping suppression, in seconds. If the interval between successive neighbor Down events is greater than resume-interval, the flapping_count is reset. In Hold-max-cost mode, if the neighbor relationship does not go Down within two successive resume-intervals or the interval between successive neighbor Down events is greater than resume-interval, the interface exits from Hold-max-cost mode. The default value is 120.";
              ext:allowDelete "false";
            }
            leaf peerFlapSuppressHoldDown {
              type boolean;
              default "false";
              description
                "Enable Hold-down mode. By default, the mode is disabled.";
            }
            leaf peerFlapSuppressDownInterval {
              when "../peerFlapSuppressHoldDown='true'";
              type uint32 {
                range "1..600";
              }
              description
                "Set the duration of the Hold-down mode, in seconds.";
              ext:allowDelete "true";
            }
            leaf peerFlapSuppressHoldMaxCost {
              type boolean;
              default "true";
              description
                "Enable Hold-max-cost mode. By default, the mode is enabled.";
            }
            leaf peerFlapSuppressStatus {
              type isiscommPeerFlapSuppressStatus;
              config false;
              description
                "Display the neighbor relationship flapping suppression status.";
            }
            leaf peerFlapCount {
              type uint32;
              config false;
              description
                "Display the current flapping_count.";
            }
            leaf peerFlapThreshold {
              type uint32;
              config false;
              description
                "Display threshold of neighbor relationship flapping suppression";
            }
            leaf peerFlapSuppressTimer {
              type string {
                length "0..40";
              }
              config false;
              description
                "Display the time when neighbor relationship flapping suppression took effect.";
            }
            leaf peerFlapSuppressRemainTimer {
              type uint32;
              config false;
              description
                "Display the remaining time of neighbor relationship flapping suppression.";
            }
            leaf meshGroupState {
              type isiscommMeshGroupState;
              default "inactive";
              description
                "Mesh-group state on an interface. If the state is Block, the interface cannot flood received LSPs.";
            }
            leaf meshGroupNumber {
              when "../meshGroupState='set'";
              type uint32 {
                range "0..4294967295";
              }
              must "not(../meshGroupState='set') or (../meshGroupState='set' and ../meshGroupNumber>=1)";
              default "1";
              description
                "Set an ID for a mesh-group. The value is an integer. When the state of the mesh-group is Set, the value ranges from 1 to 4294967295. ";
            }
            leaf incrCost {
              type uint32 {
                range "0..16777214";
              }
              default "0";
              description
                "Set the cost to be added if the link quality is low. The value is an integer ranging from 1 to 16777214. ";
            }
            leaf incrCostIpv6 {
              type uint32 {
                range "1..16777214";
              }
              description
                "Set the increase cost value about ipv6";
              ext:allowDelete "true";
            }
            leaf circuitId {
              type uint8;
              config false;
              description
                "Circuit ID of an interface.";
            }
            leaf circuitMTU {
              type uint32;
              config false;
              description
                "MTU value of an interface.";
            }
            leaf circuitL1IsDis {
              type boolean;
              config false;
              description
                "Determine whether the interface is a level-1 DIS.";
            }
            leaf circuitL2IsDis {
              type boolean;
              config false;
              description
                "Determine whether the interface is a level-2 DIS.";
            }
            leaf v4Status {
              type string {
                length "0..40";
              }
              config false;
              description
                "IPv4 status of the interface, Up or Down.";
            }
            leaf mtuState {
              type boolean;
              config false;
              description
                "MTU status of an interface, Up or Down.";
            }
            leaf linkState {
              type boolean;
              config false;
              description
                "Link status of an interface, Up or Down.";
            }
            leaf ipState {
              type boolean;
              config false;
              description
                "IPv4 address status of an interface, Up or Down.";
            }
            leaf v6Status {
              type string {
                length "0..40";
              }
              config false;
              description
                "IS-IS IPv6 status of an interface, Up or Down.";
            }
            leaf mtuV6State {
              type boolean;
              config false;
              description
                "MTU IPv6 status of an interface, Up or Down.";
            }
            leaf linkV6State {
              type boolean;
              config false;
              description
                "Link IPv6 status of an interface, Up or Down.";
            }
            leaf ipV6State {
              type boolean;
              config false;
              description
                "IPv6 address status of an interface, Up or Down.";
            }
            leaf vcState {
              type boolean;
              config false;
              description
                "Virtual Cluster status of an interface, Up or Down.";
            }
            container isHelloAuthtications {
              description
                "List of Hello packet authentication.";
              list isHelloAuthtication {
                key "levelType";
                max-elements  "2";
                description
                  "Configure an IS-IS interface to authenticate Hello packets in the specified mode and password.";
                leaf levelType {
                  type isiscommLevelType;
                  description
                    "Set the level type for authentication, which can be level-1 or level-2. This field is not required for P2P interfaces.";
                }
                leaf passwordType {
                  type isiscommAuthType;
                  mandatory true;
                  description
                    "Set the authentication password type of Hello packets, which can be simple, MD5, etc.";
                }
                leaf simplePassword {
                  when "not(../passwordType='hmac_sha256' or ../passwordType='keychain' or ../passwordType='md5') or ../passwordType='simple'";
                  type pub-type:password {
                    length "1..16";
                  }
                  description
                    "Set a plaintext. The value is a string of characters (letters or digits), spaces not supported.";
                  ext:allowDelete "true";
                }
                leaf md5Password {
                  when "not(../passwordType='keychain' or ../passwordType='simple') or ../passwordType='hmac_sha256' or ../passwordType='md5'";
                  type pub-type:passwordExtend {
                    length "1..255";
                  }
                  description
                    "Set a MD5 or HMAC-SHA256 authentication password. The value is a string of characters (letters or digits), spaces not supported.";
                  ext:allowDelete "true";
                }
                leaf serviceType {
                  when "not(../passwordType='hmac_sha256' or ../passwordType='keychain') or ../passwordType='md5' or ../passwordType='simple'";
                  type isiscommIsServiceType;
                  default "osi";
                  description
                    "Set the authentication service type, which can be IP or OSI.";
                }
                leaf sendOnly {
                  type boolean;
                  default "false";
                  description
                    "Encapsulate the authentication information in only the Hello packets to be sent.";
                }
                leaf keyId {
                  when "../passwordType='hmac_sha256'";
                  type uint16 {
                    range "0..65535";
                  }
                  default "0";
                  description
                    "Set a value for Key ID.";
                  ext:allowDelete "true";
                }
              }
            }
          }
        }
        container isSiteMTs {
          description
            "Multi-topology list.";
          list isSiteMT {
            key "addressFamily mtId";
            max-elements  "64";
            description
              "Set multi-topology parameters for an IS-IS process.";
            leaf addressFamily {
              type isiscommIsAfType;
              description
                "Address family type of the multi-topology, which can be IPv4 Address Family or IPv6 Address Family. ";
            }
            leaf mtId {
              type uint32 {
                range "0..4095";
              }
              description
                "IS-IS Multi-topology ID.";
            }
            leaf topologyName {
              type string {
                length "0..31";
              }
              description
                "Multi-topology name.";
            }
            leaf spfPriority {
              type uint32 {
                range "1..127";
              }
              default "64";
              description
                "Set a priority for multi-topology.";
            }
            leaf maxLoadBalancing {
              when "not(../mtId>2)";
              type uint32 {
                range "1..128";
              }
              default "64";
              description
                "Set the maximum number of equal-cost routes for load balancing. ";
            }
            leaf autoCostEnable {
              type boolean;
              default "false";
              description
                "Enable automatic cost calculation for the system. By default, the function is disabled.";
            }
            leaf autoCostEnableCompatible {
              when "../autoCostEnable='true'";
              type boolean;
              default "false";
              description
                "Enable automatic cost calculation compatibly for the system. By default, the function is disabled.";
            }
            leaf bandwidth {
              when "../mtId=2 and ../addressFamily='afIpv6'";
              type uint32 {
                range "1..2147483648";
              }
              default "100";
              description
                "Set the bandwidth reference used for the automatic cost calculation on an interface.The value is expressed in Mbit/s. The default value is 100.";
            }
            leaf level1Cost {
              when "../mtId=2 and ../addressFamily='afIpv6'";
              type uint32 {
                range "1..16777215";
              }
              description
                "Set the level-1 cost for an interface. If the IS-IS cost type is narrow, narrow-compatible, or compatible, the value ranges from 1 to 63. If the IS-IS cost type is wide or wide-compatible, the value ranges from 1 to 16777215.";
              ext:allowDelete "true";
            }
            leaf level2Cost {
              when "../mtId=2 and ../addressFamily='afIpv6'";
              type uint32 {
                range "1..16777215";
              }
              description
                "Set the level-2 cost for an interface. If the IS-IS cost type is narrow, narrow-compatible, or compatible, the value ranges from 1 to 63. If the IS-IS cost type is wide or wide-compatible, the value ranges from 1 to 16777215.";
              ext:allowDelete "true";
            }
            leaf overloadType {
              type isiscommIsOverLoadType;
              default "no_set";
              description
                "Configure the router to notify others that it is overloaded. The value can be No Setting, Restart Setting, or Manual Setting. The default value is No Setting.";
            }
            leaf overloadWaitType {
              type isiscommWaitType;
              default "no_wait";
              description
                "Set the overload type. The value can be Wait for BGP Convergence, Wait for Neighbor, or Not Wait. The default value is Not Wait.";
            }
            leaf overloadNbrSysId {
              type string {
                length "1..15";
              }
              description
                "Set the system ID of the neighbor. The duration for the system to keep the overload bit is set according to the status of the neighbor specified by the system ID. The length of the value is 6 bytes, in the format of XXXX.XXXX.XXXX, in which X is a hexadecimal case-insensitive character. ";
              ext:allowDelete "true";
            }
            leaf overloadTimeout1 {
              type uint32 {
                range "5..86400";
              }
              default "1200";
              description
                "If the specified neighbor does not become Up before the neighbor holdtime expires, the holdtime of the system overload flag is the neighbor holdtime. The value of neighbor holdtime is expressed in seconds, ranging from 5 to 86400. The default value is 1200.";
            }
            leaf overloadTimeout2 {
              type uint32 {
                range "5..86400";
              }
              default "600";
              description
                "If the specified neighbor becomes Up before the neighbor holdtime expires, the system overload flag keeps the neighbor timeout period. The neighbor timeout period is expressed in seconds, ranging from 5 to 86400. The default value is 600.";
            }
            leaf overloadInterlevel {
              type boolean;
              default "false";
              description
                "Determine whether a device can advertise the IP address prefixes learned from the IS-IS routes at different levels. By default, such IP address prefixes cannot be advertised.";
            }
            leaf overloadExternal {
              type boolean;
              default "false";
              description
                "Determine whether a device can advertise the IP address prefixes learned from other protocols. By default, such IP address prefixes cannot be advertised.";
            }
            leaf level1TagValue {
              when "not(../mtId>2)";
              type uint32 {
                range "0..4294967295";
              }
              default "0";
              description
                "Set the level-1 tag for an IS-IS interface. ";
              ext:allowDelete "true";
            }
            leaf level2TagValue {
              when "not(../mtId>2)";
              type uint32 {
                range "0..4294967295";
              }
              default "0";
              description
                "Set the level-2 tag for an IS-IS interface. ";
              ext:allowDelete "true";
            }
            leaf allCircBfdOn {
              type boolean;
              must "(../mtId>2 and ../allCircBfdOn='false') or (../mtId<=2)";
              default "false";
              description
                "Enable BFD on all interfaces.";
            }
            leaf frrBindingFlag {
              type boolean;
              must "(../mtId>2 and ../frrBindingFlag='false') or (../mtId<=2)";
              default "false";
              description
                "Bind the BFD status to the link status of an interface.";
            }
            leaf bfdMinRx {
              when "not(../mtId>2)";
              type uint32 {
                range "3..1000";
              }
              description
                "Set the minimum interval at which BFD packets are received. The value is expressed in milliseconds. The default value is 10. The value supported by the CX and PTN and ATN product ranges from 3 to 1000, and the value supported by other products ranges from 10 to 1000. ";
              ext:allowDelete "true";
            }
            leaf bfdMinTx {
              when "not(../mtId>2)";
              type uint32 {
                range "3..1000";
              }
              description
                "Set the minimum interval at which BFD packets are sent. The value is expressed in milliseconds. The default value is 10. The value supported by the CX and PTN and ATN product ranges from 3 to 1000, and the value supported by other products ranges from 10 to 1000. ";
              ext:allowDelete "true";
            }
            leaf bfdMultNum {
              when "not(../mtId>2)";
              type uint32 {
                range "3..50";
              }
              default "3";
              description
                "Set the detection multiplier of a BFD session. The default value is 3.";
            }
            leaf mtIndex {
              type uint32 {
                range "0..4095";
              }
              default "0";
              description
                "IS-IS multi-topology index.";
            }
            leaf attAdvControl {
              when "../mtId>2";
              type isiscommAttAdvMode;
              default "noType";
              description
                "Control to advertise the ATT bit.";
            }
            leaf attAvoidLearn {
              type boolean;
              must "(../mtId<=2 and ../attAvoidLearn='false') or ../mtId>2";
              default "false";
              description
                "Prevent the device from learning the LSPs with the ATT bit.";
            }
            leaf applyQppb {
              when "../addressFamily='afIpv6' and ../mtId<=2 and ../mtId!=1";
              type boolean;
              default "false";
              description
                "IPv6 Qppb.";
            }
            container isNextHopWeights {
              description
                "List of next hop weights.";
              list isNextHopWeight {
                when "../../mtId=0";
                key "ipAddress";
                max-elements  "131072";
                description
                  "Set a next hop weight.";
                leaf ipAddress {
                  type inet:ipv4-address-no-zone;
                  description
                    "Set A next hop address. ";
                }
                leaf weight {
                  type uint32 {
                    range "1..254";
                  }
                  default "1";
                  description
                    "Set a weight value for the next hop.";
                }
              }
            }
            container isSummaryRoutes {
              description
                "List of summary routes.";
              list isSummaryRoute {
                key "ipPrefix ipMaskLen";
                description
                  "Summary route.";
                leaf ipPrefix {
                  type inet:ip-address-no-zone;
                  description
                    "Set a summary address. ";
                }
                leaf ipMaskLen {
                  type uint8 {
                    range "0..128";
                  }
                  description
                    "Set the summary address mask. If summary address is the type of IPv4,  the max value is 32. If summary address is the type of IPv6,  the max value is 128.";
                }
                leaf levelType {
                  type isiscommLevelType;
                  must "((../levelType='level_1' or ../levelType='level_2' or ../levelType='level_1_2') )";
                  default "level_2";
                  description
                    "Set the level for summary routes. The value can be level-1, level-2, or level-1-2. The default value is level-2.";
                }
                leaf tag {
                  type uint32 {
                    range "0..4294967295";
                  }
                  default "0";
                  description
                    "Set a tag for summary routes. The value ranges from 1 to 4294967295.";
                }
                leaf genNull0Route {
                  type boolean;
                  default "false";
                  description
                    "Generate a Null 0 route to prevent routing loops.";
                }
                leaf avoidFeadBack {
                  type boolean;
                  default "false";
                  description
                    "Avoid learning summary routes.";
                }
                leaf cost {
                  type uint32 {
                    range "1..16777215";
                  }
                  default "1";
                  description
                    "Set a cost for summarized routes. If the IS-IS cost type is narrow, narrow-compatible, or compatible, the value ranges from 1 to 63. If the IS-IS cost type is wide or wide-compatible, the value ranges from 1 to 16777215.";
                }
              }
            }
            container isDefaultRoutes {
              description
                "Default route list.";
              container isDefaultRoute {
                description
                  "Enable the level-1 and level-2 routers to generate default routes.";
                leaf defaultMode {
                  type isiscommIsdefaultMode;
                  description
                    "If the value is Match Any, the route-policy name parameter is available. If the value is Always, the default routes use the Always mode. If the value is Match Default, the default routes use the Match Default mode.";
                }
                leaf policyType {
                  when "../defaultMode='matchAny'";
                  type isiscommDefaultRtPolicyType;
                  default "routePolicy";
                  description
                    "Mode of the policy used for default route. If the value is Route-Policy, the Route-Policy Name parameter is available. If the value is Xpl-Route-Policy, the Xpl-Route-Policy Name parameter is available. In None mode, the  Route-Policy and Xpl-Route-Policy are all unavailable.";
                }
                leaf routePolicyName {
                  when "../defaultMode='matchAny' or ../policyType='routePolicy'";
                  type string {
                    length "1..200";
                    pattern '.*\S.*';
                  }
                  description
                    "Set a route-policy name for default routes. ";
                  ext:allowDelete "true";
                }
                leaf routeFilterNameEntity {
                  when "../defaultMode='matchAny' or ../policyType='xplPolicy'";
                  type string {
                    length "1..1809";
                    pattern '\s*(([0-9a-zA-Z][0-9a-zA-Z\-_\.]{0,63})|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[\)]))\s*';
                  }
                  description
                    "Set a xpl route-policy name entity for default routes. ";
                  ext:allowDelete "true";
                }
                leaf cost {
                  type uint32 {
                    range "0..4261412864";
                  }
                  default "0";
                  description
                    "Set a cost for default routes. If the IS-IS cost type is narrow, narrow-compatible, or compatible, the value ranges from 1 to 63. If the IS-IS cost type is wide or wide-compatible, the value ranges from 1 to 4261412864.";
                }
                leaf tag {
                  type uint32 {
                    range "0..4294967295";
                  }
                  default "0";
                  description
                    "Set a tag for default routes. The value ranges from 1 to 4294967295. ";
                }
                leaf levelType {
                  type isiscommLevelType;
                  must "((../levelType='level_1' or ../levelType='level_2' or ../levelType='level_1_2') )";
                  default "level_2";
                  description
                    "Set a level for default routes. The value can be level-1, level-2, or level-1-2. The default value is level-2.";
                }
                leaf avoidLearning {
                  type boolean;
                  default "false";
                  description
                    "To prevent IS-IS processes from learning default routes and adding the default routes to the routing table. If the default routes that already exist in the routing table are active, the status of the route is set to inactive.";
                }
              }
            }
            container isImportRoutes {
              description
                "Import routes.";
              list isImportRoute {
                key "protocol processId";
                description
                  "Import routes of other routing protocols.";
                leaf protocol {
                  type isiscommIsImportProtT;
                  description
                    "Set the routing protocol from which routes are imported. The value can be Direct, Static, RIP, OSPF, IS-IS, or BGP. ";
                }
                leaf processId {
                  type uint32 {
                    range "0..4294967295";
                  }
                  description
                    "Set the process ID. The process ID is required when the routing protocol is RIP, OSPF, or IS-IS. The default value is 1.";
                }
                leaf costType {
                  when "../../../addressFamily='afIpv4' and ../inheritCost='false'";
                  type isiscommIsImportCostT;
                  default "external";
                  description
                    "Set the cost type for imported routes. The value can be External or Internal. The default value is External.";
                }
                leaf cost {
                  when "not(../inheritCost='true')";
                  type uint32 {
                    range "0..4261412864";
                  }
                  default "0";
                  description
                    "Set a cost for imported routes. If the IS-IS cost type is narrow, narrow-compatible, or compatible, the value ranges from 1 to 63. If the IS-IS cost type is wide or wide-compatible, the value ranges from 1 to 4261412864.";
                }
                leaf tag {
                  type uint32 {
                    range "0..4294967295";
                  }
                  default "0";
                  description
                    "Set a tag for imported routes. The value ranges from 1 to 4294967295. ";
                }
                leaf policyType {
                  type isiscommImportRtPolicyType;
                  default "noType";
                  description
                    "Mode of the policy used for import route. If the value is Route-Policy, the Route-Policy Name parameter is available. If the value is Xpl-Route-Policy, the Xpl-Route-Policy Name parameter is available. In None mode, the  Route-Policy and Xpl-Route-Policy are all unavailable.";
                }
                leaf routePolicyName {
                  when "../policyType='routePolicy'";
                  type string {
                    length "1..200";
                    pattern '.*\S.*';
                  }
                  description
                    "Set a route-policy name. ";
                  ext:allowDelete "true";
                }
                leaf routeFilterNameEntity {
                  when "../policyType='xplPolicy'";
                  type string {
                    length "1..1809";
                    pattern '\s*(([0-9a-zA-Z][0-9a-zA-Z\-_\.]{0,63})|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[\)]))\s*';
                  }
                  description
                    "Set a xpl route-policy name entity for default routes. ";
                  ext:allowDelete "true";
                }
                leaf levelType {
                  type isiscommLevelType;
                  must "((../levelType='level_1' or ../levelType='level_2' or ../levelType='level_1_2') )";
                  default "level_2";
                  description
                    "Import routes to the level-1 or (and) level-2 routing table. Level-1: Import routes to the level-1 routing table. 
Level-2: Import routes to the level-2 routing table. 
Level-1-2: Import routes to the level-1 and level-2 routing table. The default option is level-2.";
                }
                leaf inheritCost {
                  type boolean;
                  must "((../protocol='static' or ../protocol='unr' or ../protocol='all') and ../inheritCost='false') or (../protocol!='static' and ../protocol!='unr' and ../protocol!='all')";
                  default "false";
                  description
                    "Keep the original cost of a route when importing the route to IS-IS.";
                }
                leaf permitIbgp {
                  when "../protocol='bgp'";
                  type boolean;
                  default "false";
                  description
                    "Enable the device to import IBGP routes.";
                }
              }
            }
            container isFilterImports {
              description
                "Route import policy list.";
              container isFilterImport {
                when "not(../../mtId>2)";
                description
                  "Set a policy to filter received routes so that only given routes are added to the IP routing table.";
                leaf policyType {
                  type isiscommFilterType;
                  description
                    "Set the policy mode for route filtering. In ACL mode, the ACL Number parameter is available. In Route-Policy mode, the Route-Policy Name parameter is available. In IP Prefix mode, the IP Prefix parameter is available. In None mode, the ACL Number, Route-Policy Name, and IP Prefix parameters are all unavailable.";
                }
                leaf aclNumOrName {
                  when "not(../policyType='aclNumOrName' and ../../../addressFamily='afIpv6') or ../policyType='aclNumOrName' and ../../../addressFamily='afIpv4' or ../policyType='aclNumOrName'";
                  type string {
                    length "1..64";
                    pattern '\s*(2[0-9]{3}|[a-zA-Z]\S*)\s*';
                  }
                  description
                    "Set an ACL number or name used for route filtering. The ACL number ranges from 2000 to 2999. The ACL name must start with a letter, and the ACL name is case-sensitive.";
                  ext:allowDelete "true";
                }
                leaf acl6NumOrName {
                  when "not(../policyType='aclNumOrName' and ../../../addressFamily='afIpv4') or ../policyType='aclNumOrName' and ../../../addressFamily='afIpv6' or ../policyType='aclNumOrName'";
                  type string {
                    length "1..64";
                    pattern '\s*(2[0-9]{3}|[a-zA-Z]\S*)\s*';
                  }
                  description
                    "Set an ACL6 number or name used for route filtering. The ACL6 number ranges from 2000 to 2999. The ACL6 name must start with a letter, and the ACL6 name is case-sensitive.";
                  ext:allowDelete "true";
                }
                leaf ipPrefix {
                  when "not(../policyType='ipPrefix' and ../../../addressFamily='afIpv6') or ../policyType='ipPrefix' and ../../../addressFamily='afIpv4' or ../policyType='ipPrefix'";
                  type string {
                    length "1..169";
                    pattern '.*\S.*';
                  }
                  description
                    "Set the name of an IP prefix list.";
                  ext:allowDelete "true";
                }
                leaf ipv6Prefix {
                  when "not(../policyType='ipPrefix' and ../../../addressFamily='afIpv4') or ../policyType='ipPrefix' and ../../../addressFamily='afIpv6' or ../policyType='ipPrefix'";
                  type string {
                    length "1..169";
                    pattern '.*\S.*';
                  }
                  description
                    "Set the name of an IPv6 prefix list.";
                  ext:allowDelete "true";
                }
                leaf routePolicyName {
                  when "../policyType='routePolicy'";
                  type string {
                    length "1..200";
                    pattern '.*\S.*';
                  }
                  description
                    "Set the name of a route-policy which filters routes based on the tag or other protocol parameters.";
                  ext:allowDelete "true";
                }
                leaf routeFilterNameEntity {
                  when "../policyType='xplPolicy'";
                  type string {
                    length "1..1809";
                    pattern '\s*(([0-9a-zA-Z][0-9a-zA-Z\-_\.]{0,63})|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[\)]))\s*';
                  }
                  description
                    "Set a xpl route-policy name entity for default routes. ";
                  ext:allowDelete "true";
                }
              }
            }
            container isFilterExports {
              description
                "Route export policy list.";
              list isFilterExport {
                when "not(../../mtId>2)";
                key "protocol processId";
                description
                  "Set an export policy to filter the imported routes to be advertised.";
                leaf protocol {
                  type isiscommIsImportProtT;
                  description
                    "Route protocol, specifying which imported routes need to be filtered during route advertisement. The value can be Direct, Static, RIP, RIPNG, BGP, OSPF, OSPFV3, or other IS-IS processes. If this parameter is not set, all routes to be advertised are filtered.";
                }
                leaf processId {
                  type uint32 {
                    range "0..4294967295";
                  }
                  description
                    "Set the process ID. The process ID is required when the routing protocol is RIP, RIPNG, OSPF, OSPFV3, or IS-IS. The default value is 1.";
                }
                leaf policyType {
                  type isiscommFilterType;
                  mandatory true;
                  description
                    "Set the policy mode for route filtering. In ACL mode, the ACL Number parameter is available. In Route-Policy mode, the Route-Policy Name parameter is available. In IP Prefix mode, the IP Prefix parameter is available. In None mode, the ACL Number, Route-Policy Name, and IP Prefix parameters are all unavailable.";
                }
                leaf aclNumOrName {
                  when "not(../policyType='aclNumOrName' and ../../../addressFamily='afIpv6') or ../policyType='aclNumOrName' and ../../../addressFamily='afIpv4' or ../policyType='aclNumOrName'";
                  type string {
                    length "1..64";
                    pattern '^\s*(2[0-9]{3}|[a-zA-Z]\S*)\s*$';
                  }
                  description
                    "To set the ACL (Access Control List) number or name used for route filtering. The ACL number ranges from 2000 to 2999. The ACL name must start with letter, and the ACL name is case-sensitive.";
                  ext:allowDelete "true";
                }
                leaf acl6NumOrName {
                  when "not(../policyType='aclNumOrName' and ../../../addressFamily='afIpv4') or ../policyType='aclNumOrName' and ../../../addressFamily='afIpv6' or ../policyType='aclNumOrName'";
                  type string {
                    length "1..64";
                    pattern '\s*(2[0-9]{3}|[a-zA-Z]\S*)\s*';
                  }
                  description
                    "To set the ACL6 (Access Control List IPv6) number or name used for route filtering. The ACL6 number ranges from 2000 to 2999. The ACL6 name must start with a letter, and the ACL6 name is case-sensitive.";
                  ext:allowDelete "true";
                }
                leaf ipPrefix {
                  when "not(../policyType='ipPrefix' and ../../../addressFamily='afIpv6') or ../policyType='ipPrefix' and ../../../addressFamily='afIpv4' or ../policyType='ipPrefix'";
                  type string {
                    length "1..169";
                    pattern '.*\S.*';
                  }
                  description
                    "Name of the IP address prefix list.";
                  ext:allowDelete "true";
                }
                leaf ipv6Prefix {
                  when "not(../policyType='ipPrefix' and ../../../addressFamily='afIpv4') or ../policyType='ipPrefix' and ../../../addressFamily='afIpv6' or ../policyType='ipPrefix'";
                  type string {
                    length "1..169";
                    pattern '.*\S.*';
                  }
                  description
                    "Name of the IPv6 address prefix list.";
                  ext:allowDelete "true";
                }
                leaf routePolicyName {
                  when "../policyType='routePolicy'";
                  type string {
                    length "1..200";
                    pattern '.*\S.*';
                  }
                  description
                    "Name of the routing policy which defines that routes are filtered based on the label and other protocol parameters.";
                  ext:allowDelete "true";
                }
                leaf routeFilterNameEntity {
                  when "../policyType='xplPolicy'";
                  type string {
                    length "1..1809";
                    pattern '\s*(([0-9a-zA-Z][0-9a-zA-Z\-_\.]{0,63})|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[\)]))\s*';
                  }
                  description
                    "Set a xpl route-policy name entity for default routes. ";
                  ext:allowDelete "true";
                }
              }
            }
            container isLeakRouteLevel2ToLevel1s {
              description
                "List of level-2 to level-1 route leaking.";
              container isLeakRouteLevel2ToLevel1 {
                description
                  "Information used to control IS-IS to perform route leaking from level-2 to level-1. This command needs to be set on the level-1-2 router connected to the external areas.";
                leaf tag {
                  type uint32 {
                    range "0..4294967295";
                  }
                  default "0";
                  description
                    "Management label value assigned for imported routes. The label value is the name of route filtering during route leaking.";
                }
                leaf policyType {
                  type isiscommIsPolicyType;
                  default "noType";
                  description
                    "Mode of the policy used for route leaking. If the value is ACL, the ACL number parameter is available. If the value is Route-Policy, the Route-Policy Name parameter is available. If the value is IP Prefix, the IP Prefix parameter is available. In None mode, the ACL Number, Route-Policy Name, and IP Prefix parameters are all unavailable.";
                }
                leaf routePolicyName {
                  when "../policyType='routePolicy'";
                  type string {
                    length "1..200";
                    pattern '.*\S.*';
                  }
                  description
                    "Name of the route filtering policy used during route leaking.";
                  ext:allowDelete "true";
                }
                leaf routeFilterNameEntity {
                  when "../policyType='xplPolicy'";
                  type string {
                    length "1..1809";
                    pattern '\s*(([0-9a-zA-Z][0-9a-zA-Z\-_\.]{0,63})|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[\)]))\s*';
                  }
                  description
                    "Set a xpl route-policy name entity for default routes. ";
                  ext:allowDelete "true";
                }
                leaf aclNumOrName {
                  when "not(../../../addressFamily='afIpv6' and ../policyType='aclNumOrName' or ../policyType!='aclNumOrName') or ../../../addressFamily='afIpv4' and ../policyType='aclNumOrName'";
                  type string {
                    length "1..64";
                    pattern '\s*(2[0-9]{3}|[a-zA-Z]\S*)\s*';
                  }
                  description
                    "Set an ACL number or name used for route filtering. The ACL number ranges from 2000 to 2999. The ACL name must start with a letter, and the ACL name is case-sensitive.";
                  ext:allowDelete "true";
                }
                leaf acl6NumOrName {
                  when "not(../../../addressFamily='afIpv4' and ../policyType='aclNumOrName' or ../policyType!='aclNumOrName') or ../../../addressFamily='afIpv6' and ../policyType='aclNumOrName'";
                  type string {
                    length "1..64";
                    pattern '\s*(2[0-9]{3}|[a-zA-Z]\S*)\s*';
                  }
                  description
                    "Set an ACL6 number or name used for route filtering. The ACL6 number ranges from 2000 to 2999. The ACL6 name must start with a letter, and the ACL6 name is case-sensitive.";
                  ext:allowDelete "true";
                }
                leaf ipPrefix {
                  when "not(../policyType='ipPrefix' and ../../../addressFamily='afIpv6') or ../policyType='ipPrefix' and ../../../addressFamily='afIpv4' or ../policyType='ipPrefix'";
                  type string {
                    length "1..169";
                    pattern '.*\S.*';
                  }
                  description
                    "Set the name of an IP prefix list. Only the routes that match the IP prefix list can leak into a level-1 area.";
                  ext:allowDelete "true";
                }
                leaf ipv6Prefix {
                  when "not(../policyType='ipPrefix' and ../../../addressFamily='afIpv4') or ../policyType='ipPrefix' and ../../../addressFamily='afIpv6' or ../policyType='ipPrefix'";
                  type string {
                    length "1..169";
                    pattern '.*\S.*';
                  }
                  description
                    "Set the name of an IPv6 prefix list. Only the routes that match the IPv6 prefix list can leak into a level-1 area.";
                  ext:allowDelete "true";
                }
                leaf allowFilter {
                  type boolean;
                  default "false";
                  description
                    "Set the name of a route-policy which filters routes based on the tag or other protocol parameters.";
                }
                leaf allowUpdown {
                  type boolean;
                  default "false";
                  description
                    "Set the Up/Down bit for routes.";
                }
              }
            }
            container isLeakRouteLevel1ToLevel2s {
              description
                "List of level-1 to level-2 route leaking.";
              container isLeakRouteLevel1ToLevel2 {
                description
                  "Control the leaking of the routes from a level-1 area to a level-2 area. This is convenient for route management. This command needs to be configured on the level-1-2 router connected to external areas.";
                leaf tag {
                  when "../leakEnableFlag='true'";
                  type uint32 {
                    range "0..4294967295";
                  }
                  default "0";
                  description
                    "Administrative tag assigned for imported routes.";
                }
                leaf policyType {
                  when "../leakEnableFlag='true'";
                  type isiscommIsPolicyType;
                  default "noType";
                  description
                    "Mode of the policy used for route leaking. If the value is ACL, the ACL number parameter is available. If the value is Route-Policy, the Route-Policy Name parameter is available. If the value is IP Prefix, the IP Prefix parameter is available. In None mode, the ACL Number, Route Policy Name, and IP Prefix parameters are all unavailable.";
                }
                leaf routePolicyName {
                  when "../leakEnableFlag='true' or ../policyType='routePolicy'";
                  type string {
                    length "1..200";
                    pattern '.*\S.*';
                  }
                  description
                    "Route-policy name used during route leaking.";
                  ext:allowDelete "true";
                }
                leaf routeFilterNameEntity {
                  when "../policyType='xplPolicy'";
                  type string {
                    length "1..1809";
                    pattern '\s*(([0-9a-zA-Z][0-9a-zA-Z\-_\.]{0,63})|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[\)]))\s*';
                  }
                  description
                    "Set a xpl route-policy name entity for default routes. ";
                  ext:allowDelete "true";
                }
                leaf aclNumOrName {
                  when "not(../../../addressFamily='afIpv6' and ../policyType='aclNumOrName' or ../policyType!='aclNumOrName') or ../../../addressFamily='afIpv4' and ../policyType='aclNumOrName' or ../leakEnableFlag='true'";
                  type string {
                    length "1..64";
                    pattern '\s*(2[0-9]{3}|[a-zA-Z]\S*)\s*';
                  }
                  description
                    "Set an ACL number or name used for route filtering. The ACL number ranges from 2000 to 2999. The ACL name must start with a letter, and the ACL name is case-sensitive.";
                  ext:allowDelete "true";
                }
                leaf acl6NumOrName {
                  when "not(../../../addressFamily='afIpv4' and ../policyType='aclNumOrName' or ../policyType!='aclNumOrName') or ../../../addressFamily='afIpv6' and ../policyType='aclNumOrName' or ../leakEnableFlag='true'";
                  type string {
                    length "1..64";
                    pattern '\s*(2[0-9]{3}|[a-zA-Z]\S*)\s*';
                  }
                  description
                    "Set an ACL6 number or name used for route filtering. The IPv6 ACL number ranges from 2000 to 2999. The IPv6 ACL name must start with a letter, and the IPv6 ACL name is case-sensitive.";
                  ext:allowDelete "true";
                }
                leaf ipPrefix {
                  when "not(../policyType='ipPrefix' and ../../../addressFamily='afIpv6') or ../leakEnableFlag='true' or ../policyType='ipPrefix' and ../../../addressFamily='afIpv4' or ../policyType='ipPrefix'";
                  type string {
                    length "1..169";
                    pattern '.*\S.*';
                  }
                  description
                    "Set the name of an IP prefix list. Only the routes that match the IP prefix list can leak into a level-2 area.";
                  ext:allowDelete "true";
                }
                leaf ipv6Prefix {
                  when "not(../policyType='ipPrefix' and ../../../addressFamily='afIpv4') or ../leakEnableFlag='true' or ../policyType='ipPrefix' and ../../../addressFamily='afIpv6' or ../policyType='ipPrefix'";
                  type string {
                    length "1..169";
                    pattern '.*\S.*';
                  }
                  description
                    "Set the name of an IPv6 prefix list. Only the routes that match the IPv6 prefix list can leak into a level-2 area.";
                  ext:allowDelete "true";
                }
                leaf leakEnableFlag {
                  type boolean;
                  default "true";
                  description
                    "Enable level-1 to level-2 route filtering.";
                }
                leaf allowFilter {
                  when "../leakEnableFlag='true'";
                  type boolean;
                  default "false";
                  description
                    "Set the name of a route-policy which filters routes based on the tag or other protocol parameters.";
                }
              }
            }
            container isRoutePrioritys {
              description
                "Route priority list.";
              list isRoutePriority {
                when "not(../../mtId>2)";
                key "isLevel priority";
                description
                  "Set a route priority.";
                leaf isLevel {
                  type isiscommLevelType;
                  description
                    "Set a level type for the route priority, which can be level-1 or level-2.";
                }
                leaf priority {
                  type isiscommRoutePriorityType;
                  description
                    "Set a route priority.";
                }
                leaf useflag {
                  type isiscommRoutePriorityFlag;
                  mandatory true;
                  description
                    "Set a filtering policy for the route priority.";
                }
                leaf tag {
                  when "not(../useflag='ipPrefix' and ../../../addressFamily='afIpv4' or ../useflag='ipPrefix' and ../../../addressFamily='afIpv6' or not(../useflag)) or ../useflag='tag'";
                  type uint32 {
                    range "0..4294967295";
                  }
                  must "not(../useflag='tag') or (../useflag='tag' and ../tag>=1)";
                  default "0";
                  description
                    "Set a tag for the route priority. The value is an integer. The default value is 0, which cannot be configured.";
                }
                leaf ipprefix {
                  when "not(../useflag='ipPrefix' and ../../../addressFamily='afIpv6' or ../useflag='tag' or not(../useflag)) or ../useflag='ipPrefix' and ../../../addressFamily='afIpv4'";
                  type string {
                    length "1..169";
                    pattern '.*\S.*';
                  }
                  description
                    "Set the name of an IP prefix list.";
                  ext:allowDelete "true";
                }
                leaf ipv6prefix {
                  when "not(../useflag='ipPrefix' and ../../../addressFamily='afIpv4' or ../useflag='tag' or not(../useflag)) or ../useflag='ipPrefix' and ../../../addressFamily='afIpv6'";
                  type string {
                    length "1..169";
                    pattern '.*\S.*';
                  }
                  description
                    "Set the name of an IPv6 prefix list.";
                  ext:allowDelete "true";
                }
              }
            }
            container isPreferences {
              description
                "Priority list.";
              container isPreference {
                description
                  "Set a priority for IS-IS.";
                leaf policyType {
                  type isiscommPreferenceType;
                  default "noType";
                  description
                    "Mode of the policy used for applying the routing protocol priority. If the value is ACL, the ACL number parameter is available. If the value is Route-Policy, the Route-Policy Name parameter is available. If the value is IP Prefix, the IP Prefix parameter is available.";
                }
                leaf preferenceValue {
                  type uint32 {
                    range "1..255";
                  }
                  default "15";
                  description
                    "Set the priority for protocols. The smaller the value, the higher the priority.";
                }
                leaf routePolicyName {
                  when "../policyType='routePolicy'";
                  type string {
                    length "1..200";
                    pattern '.*\S.*';
                  }
                  description
                    "Name of a route filtering policy.";
                  ext:allowDelete "true";
                }
                leaf routeFilterNameEntity {
                  when "../policyType='xplPolicy'";
                  type string {
                    length "1..1809";
                    pattern '\s*(([0-9a-zA-Z][0-9a-zA-Z\-_\.]{0,63})|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[\)]))\s*';
                  }
                  description
                    "Set a xpl route-policy name entity for default routes. ";
                  ext:allowDelete "true";
                }
              }
            }
            container isFrr {
              when "not(../mtId>2)";
              description
                "Enable FRR.";
              leaf frrEnable {
                type boolean;
                default "false";
                description
                  "Enable FRR.";
              }
              leaf policyType {
                when "not(../frrEnable='false' and ../../addressFamily!='afIpv4' or ../frrEnable='false' and ../../addressFamily='afIpv4' and ../../mtId=0 or ../frrEnable='false' and ../../mtId!=0) or ../frrEnable='true'";
                type isiscommFrrPolicyType;
                default "noType";
                description
                  "LFA Policy type.";
              }
              leaf routePolicyName {
                when "not(../frrEnable='false' and ../../addressFamily!='afIpv4' or ../frrEnable='false' and ../../addressFamily='afIpv4' and ../../mtId=0 or ../frrEnable='false' and ../../mtId!=0) or ../policyType='routePolicy'";
                type string {
                  length "1..200";
                  pattern '.*\S.*';
                }
                description
                  "LFA Policy name.";
                ext:allowDelete "true";
              }
              leaf routeFilterNameEntity {
                when "not(../frrEnable='false' and ../../addressFamily!='afIpv4' or ../frrEnable='false' and ../../addressFamily='afIpv4' and ../../mtId=0 or ../frrEnable='false' and ../../mtId!=0) or ../policyType='xplPolicy'";
                type string {
                  length "1..1809";
                  pattern '\s*(([0-9a-zA-Z][0-9a-zA-Z\-_\.]{0,63})|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[,][0-9a-zA-Z][0-9a-zA-Z\-_\.]{0,63}[\)])|([0-9a-zA-Z][0-9a-zA-Z\-_\.]{0,63}[\(][0-9a-zA-Z][0-9a-zA-Z\-_\.]{0,63}[\)]))\s*';
                }
                description
                  "Set a xpl route-policy name entity for default routes. ";
                ext:allowDelete "true";
              }
              leaf lfaLevel1Enable {
                when "not(../frrEnable='false' and ../../addressFamily!='afIpv4' or ../frrEnable='false' and ../../addressFamily='afIpv4' and ../../mtId=0 or ../frrEnable='false' and ../../mtId!=0) or ../frrEnable='true'";
                type boolean;
                default "false";
                description
                  "Enable IS-IS auto FRR of Level-1 and calculate loop-free-alternate routes using the LFA arithmetic.";
              }
              leaf lfaLevel2Enable {
                when "not(../frrEnable='false' and ../../addressFamily!='afIpv4' or ../frrEnable='false' and ../../addressFamily='afIpv4' and ../../mtId=0 or ../frrEnable='false' and ../../mtId!=0) or ../frrEnable='true'";
                type boolean;
                default "false";
                description
                  "Enable IS-IS auto FRR of Level-2 and calculate loop-free-alternate routes using the LFA arithmetic.";
              }
              container isRlfa {
                when "not(../frrEnable='false' and ../../addressFamily!='afIpv4' or ../frrEnable='false')";
                description
                  "RLFA enabling.";
                leaf rlfaLevel1Enable {
                  when "../../frrEnable='true' and ../../../addressFamily='afIpv4' and ../../../mtId=0";
                  type boolean;
                  default "false";
                  description
                    "Enable level-1 remote LFA.";
                }
                leaf rlfaLevel1MaxCost {
                  when "not(../../frrEnable='true' and ../../../addressFamily='afIpv4' and ../../../mtId=0 and ../rlfaLevel1Enable='false' and ../rlfaLevel2Enable='false' or ../../frrEnable='true' and ../../../addressFamily='afIpv4' and ../../../mtId=0 and ../rlfaLevel1Enable='false' and ../rlfaLevel2Enable='true') or ../../frrEnable='true' and ../../../addressFamily='afIpv4' and ../../../mtId=0 and ../rlfaLevel1Enable='true' and ../rlfaLevel2Enable='false' or ../../frrEnable='true' and ../../../addressFamily='afIpv4' and ../../../mtId=0 and ../rlfaLevel1Enable='true' and ../rlfaLevel2Enable='true'";
                  type uint32 {
                    range "1..4261412864";
                  }
                  default "4261412864";
                  description
                    "Remote-lfa tunnel ldp maximum-reachable-cost level-1.";
                }
                leaf rlfaLevel1IpPrefix {
                  when "../../frrEnable='true' and ../../../addressFamily='afIpv4' and ../../../mtId=0 and ../rlfaLevel1Enable='false' and ../rlfaLevel2Enable='false' or ../../frrEnable='true' and ../../../addressFamily='afIpv4' and ../../../mtId=0 and ../rlfaLevel1Enable='false' and ../rlfaLevel2Enable='true' or ../../frrEnable='true' and ../../../addressFamily='afIpv4' and ../../../mtId=0 and ../rlfaLevel1Enable='true' and ../rlfaLevel2Enable='false' or ../../frrEnable='true' and ../../../addressFamily='afIpv4' and ../../../mtId=0 and ../rlfaLevel1Enable='true' and ../rlfaLevel2Enable='true'";
                  type string {
                    length "1..169";
                    pattern '.*\S.*';
                  }
                  description
                    "Filter PQ node.Those nodes which don't pass filter can't be PQ node";
                  ext:allowDelete "true";
                }
                leaf rlfaLevel2Enable {
                  when "../../frrEnable='true' and ../../../addressFamily='afIpv4' and ../../../mtId=0";
                  type boolean;
                  default "false";
                  description
                    "Enable level-2 remote LFA.";
                }
                leaf rlfaLevel2MaxCost {
                  when "not(../../frrEnable='true' and ../../../addressFamily='afIpv4' and ../../../mtId=0 and ../rlfaLevel1Enable='false' and ../rlfaLevel2Enable='false' or ../../frrEnable='true' and ../../../addressFamily='afIpv4' and ../../../mtId=0 and ../rlfaLevel1Enable='true' and ../rlfaLevel2Enable='false') or ../../frrEnable='true' and ../../../addressFamily='afIpv4' and ../../../mtId=0 and ../rlfaLevel1Enable='false' and ../rlfaLevel2Enable='true' or ../../frrEnable='true' and ../../../addressFamily='afIpv4' and ../../../mtId=0 and ../rlfaLevel1Enable='true' and ../rlfaLevel2Enable='true'";
                  type uint32 {
                    range "1..4261412864";
                  }
                  default "4261412864";
                  description
                    "Remote-lfa tunnel ldp maximum-reachable-cost level-2.";
                }
                leaf rlfaLevel2IpPrefix {
                  when "../../frrEnable='true' and ../../../addressFamily='afIpv4' and ../../../mtId=0 and ../rlfaLevel1Enable='false' and ../rlfaLevel2Enable='false' or ../../frrEnable='true' and ../../../addressFamily='afIpv4' and ../../../mtId=0 and ../rlfaLevel1Enable='false' and ../rlfaLevel2Enable='true' or ../../frrEnable='true' and ../../../addressFamily='afIpv4' and ../../../mtId=0 and ../rlfaLevel1Enable='true' and ../rlfaLevel2Enable='false' or ../../frrEnable='true' and ../../../addressFamily='afIpv4' and ../../../mtId=0 and ../rlfaLevel1Enable='true' and ../rlfaLevel2Enable='true'";
                  type string {
                    length "1..169";
                    pattern '.*\S.*';
                  }
                  description
                    "Filter PQ node.Those nodes which don't pass filter can't be PQ node.";
                  ext:allowDelete "true";
                }
              }
              container isFrrTieBreak {
                when "not(../frrEnable='false' and ../../addressFamily!='afIpv4' or ../frrEnable='false' and ../../addressFamily='afIpv4' and ../../mtId=0 or ../frrEnable='false' and ../../mtId!=0 or ../frrEnable='true' and ../lfaLevel2Enable!='true' and ../lfaLevel1Enable!='true')";
                description
                  "Configuring a Rule of Selecting a Backup Path for IS-IS Auto FRR.";
                leaf l1nodeProtectPrefer {
                  when "not(../../frrEnable='true' and ../../lfaLevel2Enable='true' and ../../lfaLevel1Enable!='true') or ../../frrEnable='true' and ../../lfaLevel1Enable='true' and ../../lfaLevel2Enable='true' or ../../frrEnable='true' and ../../lfaLevel2Enable!='true' and ../../lfaLevel1Enable='true'";
                  type uint8 {
                    range "1..255";
                  }
                  default "40";
                  description
                    "Set the value of level1 node protect prefer,the default vale is 40.";
                }
                leaf l1lowcostPrefer {
                  when "not(../../frrEnable='true' and ../../lfaLevel2Enable='true' and ../../lfaLevel1Enable!='true') or ../../frrEnable='true' and ../../lfaLevel1Enable='true' and ../../lfaLevel2Enable='true' or ../../frrEnable='true' and ../../lfaLevel2Enable!='true' and ../../lfaLevel1Enable='true'";
                  type uint8 {
                    range "1..255";
                  }
                  default "20";
                  description
                    "Set the value of level1 lowcost prefer,the default vale is 20.";
                }
                leaf l2nodeProtectPrefer {
                  when "not(../../frrEnable='true' and ../../lfaLevel2Enable!='true' and ../../lfaLevel1Enable='true') or ../../frrEnable='true' and ../../lfaLevel1Enable='true' and ../../lfaLevel2Enable='true' or ../../frrEnable='true' and ../../lfaLevel2Enable='true' and ../../lfaLevel1Enable!='true'";
                  type uint8 {
                    range "1..255";
                  }
                  default "40";
                  description
                    "Set the value of level2 node protect prefer,the default vale is 40.";
                }
                leaf l2lowcostPrefer {
                  when "not(../../frrEnable='true' and ../../lfaLevel2Enable!='true' and ../../lfaLevel1Enable='true') or ../../frrEnable='true' and ../../lfaLevel1Enable='true' and ../../lfaLevel2Enable='true' or ../../frrEnable='true' and ../../lfaLevel2Enable='true' and ../../lfaLevel1Enable!='true'";
                  type uint8 {
                    range "1..255";
                  }
                  default "20";
                  description
                    "Set the value of level2 lowcost prefer,the default vale is 20.";
                }
              }
              container isTilfa {
                when "not(../frrEnable='false' and ../../addressFamily!='afIpv4' or ../frrEnable='false' and ../../addressFamily='afIpv4' and ../../mtId=0 or ../frrEnable='false' and ../../mtId!=0 or ../frrEnable='true' and ../../addressFamily!='afIpv4' or ../frrEnable='true' and ../../mtId!=0) or ../frrEnable='true' and ../../addressFamily='afIpv4' and ../../mtId=0";
                description
                  "Enable TI-LFA.";
                leaf tilfaL1Enable {
                  when "../../frrEnable='true' and ../../../addressFamily='afIpv4' and ../../../mtId=0";
                  type boolean;
                  default "false";
                  description
                    "Enable Level-1 TI-LFA.";
                }
                leaf tilfaL2Enable {
                  when "../../frrEnable='true' and ../../../addressFamily='afIpv4' and ../../../mtId=0";
                  type boolean;
                  default "false";
                  description
                    "Enable Level-2 TI-LFA.";
                }
              }
            }
            container isCircMts {
              description
                "Interface multi-topology list.";
              list isCircMt {
                key "ifName";
                max-elements  "64";
                description
                  "Set parameters for IS-IS multi-topology on an interface.";
                leaf ifName {
                  type leafref {
                    path "/ifm:ifm/ifm:interfaces/ifm:interface/ifm:ifName";
                  }
                  description
                    "Interface name.";
                }
                leaf level1Cost {
                  type uint32 {
                    range "0..16777215";
                  }
                  description
                    "Set the link cost for an interface during the level-1 SPF calculation. If the IS-IS cost type is narrow, narrow-compatible, or compatible, the value ranges from 1 to 63. If the IS-IS cost type is wide or wide-compatible, the value ranges from 1 to 16777215.The interface of LoopBack can use the value of 0.";
                  ext:allowDelete "true";
                }
                leaf level2Cost {
                  type uint32 {
                    range "0..16777215";
                  }
                  description
                    "Set the link cost for an interface during the level-2 SPF calculation. If the IS-IS cost type is narrow, narrow-compatible, or compatible, the value ranges from 1 to 63. If the IS-IS cost type is wide or wide-compatible, the value ranges from 1 to 16777215.The interface of LoopBack can use the value of 0.";
                  ext:allowDelete "true";
                }
                leaf level1Tag {
                  type uint32 {
                    range "0..4294967295";
                  }
                  default "0";
                  description
                    "Set the level-1 tag value for direct routes on the interface.";
                  ext:allowDelete "true";
                }
                leaf level2Tag {
                  type uint32 {
                    range "0..4294967295";
                  }
                  default "0";
                  description
                    "Set the level-2 tag value for direct routes on the interface. ";
                  ext:allowDelete "true";
                }
                leaf suppressReach {
                  when "../../../mtId<=2";
                  type isiscommLevelTypeWithZero;
                  default "no_set";
                  description
                    "Suppress the advertisement of direct route. By default, direct routes can be advertised.";
                }
                leaf bfdEnable {
                  type boolean;
                  must "(../../../mtId>2 and ../bfdEnable='false') or (../../../mtId<=2)";
                  default "false";
                  description
                    "Enable dynamic BFD on an interface. By default, dynamic BFD is disabled.";
                }
                leaf bfdStaticEn {
                  type boolean;
                  must "(../../../mtId>2 and ../bfdStaticEn='false') or (../../../mtId<=2)";
                  default "false";
                  description
                    "Enable static BFD on an interface. By default, static BFD is disabled.";
                }
                leaf bfdBlockEn {
                  type boolean;
                  must "(../../../mtId>2 and ../bfdBlockEn='false') or (../../../mtId<=2)";
                  default "false";
                  description
                    "Disable dynamic BFD from an interface. By default, dynamic BFD is not blocked.";
                }
                leaf bfdMinRx {
                  when "../../../mtId<=2";
                  type uint32 {
                    range "3..1000";
                  }
                  description
                    "Set the minimum interval at which BFD packets are received. The value is expressed in milliseconds. The default value is 10. The value supported by the CX and PTN and ATN product ranges from 3 to 1000, and the value supported by other products ranges from 10 to 1000. ";
                  ext:allowDelete "true";
                }
                leaf bfdMinTx {
                  when "../../../mtId<=2";
                  type uint32 {
                    range "3..1000";
                  }
                  description
                    "Set the minimum interval at which BFD packets are sent. The value is expressed in milliseconds. The default value is 10. The value supported by the CX and PTN and ATN product ranges from 3 to 1000, and the value supported by other products ranges from 10 to 1000. ";
                  ext:allowDelete "true";
                }
                leaf bfdMultiplierNumber {
                  when "../../../mtId<=2";
                  type uint32 {
                    range "3..50";
                  }
                  default "3";
                  description
                    "Set the detection multiplier of a BFD session. The default value is 3.";
                }
                leaf frrBindingFlag {
                  type boolean;
                  must "(../../../mtId>2 and ../frrBindingFlag='false') or (../../../mtId<=2)";
                  default "false";
                  description
                    "Bind the BFD status to the link status of an interface.";
                }
                leaf level1FrrBlock {
                  type boolean;
                  default "false";
                  description
                    "Prevent an interface from participating Level-1 LFA Backup Interface calculation in a IPv6 base topology.";
                }
                leaf level2FrrBlock {
                  type boolean;
                  default "false";
                  description
                    "Prevent an interface from participating Level-2 LFA Backup Interface calculation in a topology.";
                }
                leaf level1RemoteLFA {
                  type boolean;
                  default "false";
                  description
                    "Disable Level-1 RLFA of the Interface.";
                }
                leaf level2RemoteLFA {
                  type boolean;
                  default "false";
                  description
                    "Disable Level-2 RLFA of the Interface.";
                }
                leaf l1TilfaDisable {
                  type boolean;
                  default "false";
                  config false;
                  description
                    "Whether an interface is prevented from being calculated as a valid backup interface during Level-1 LFA calculation in the IPv4 MT.";
                }
                leaf l2TilfaDisable {
                  type boolean;
                  default "false";
                  config false;
                  description
                    "Whether an interface is prevented from being calculated as a valid backup interface during Level-2 LFA calculation in the IPv4 MT.";
                }
                container isPrefixSid {
                  description
                    "Information of prefix sid.";
                  leaf prefixSidType {
                    type isiscommPrefixSidType;
                    default "no_set";
                    description
                      "Set the type of prefix sid.";
                  }
                  leaf prefixLabel {
                    type uint32 {
                      range "0..1048575";
                    }
                    must "not(../prefixSidType='no_set') or (../prefixSidType='no_set' and ../prefixLabel=0)";
                    default "0";
                    description
                      "Set the label of prefix sid.";
                  }
                  leaf nodeFlag {
                    type boolean;
                    must "not(../prefixSidType='no_set')";
                    default "true";
                    description
                      "Set the node flag.";
                  }
                }
              }
            }
            container isDispRouteStatisticss {
              config false;
              description
                "Route statistics information list.";
              list isDispRouteStatistics {
                key "levelType";
                config false;
                description
                  "Routing statistics.";
                leaf levelType {
                  type isiscommLevelType;
                  config false;
                  description
                    "Level type, level-1 or level-2. ";
                }
                leaf v4LearntRtNum {
                  type uint32;
                  config false;
                  description
                    "Number of learned IPv4 routes.";
                }
                leaf v6LearntRtNum {
                  type uint32;
                  config false;
                  description
                    "Number of learned IPv6 routes.";
                }
                leaf v4CriticalRtNum {
                  type uint32;
                  config false;
                  description
                    "Number of IPv4 routes with priority critical.";
                }
                leaf v4HighRtNum {
                  type uint32;
                  config false;
                  description
                    "Number of IPv4 routes with priority high.";
                }
                leaf v4MediumRtNum {
                  type uint32;
                  config false;
                  description
                    "Number of IPv4 routes with priority medium.";
                }
                leaf v4LowRtNum {
                  type uint32;
                  config false;
                  description
                    "Number of IPv4 routes with priority low.";
                }
                leaf v6CriticalRtNum {
                  type uint32;
                  config false;
                  description
                    "Number of IPv6 routes with priority critical.";
                }
                leaf v6HighRtNum {
                  type uint32;
                  config false;
                  description
                    "Number of IPv4 routes with priority high.";
                }
                leaf v6MediumRtNum {
                  type uint32;
                  config false;
                  description
                    "Number of IPv6 routes with priority medium.";
                }
                leaf v6LowRtNum {
                  type uint32;
                  config false;
                  description
                    "Number of IPv6 routes with priority low.";
                }
                leaf v4ForwardRtNum {
                  type uint32;
                  config false;
                  description
                    "Number of IPv4 routes.";
                }
                leaf v6ForwardRtNum {
                  type uint32;
                  config false;
                  description
                    "Number of IPv6 routes.";
                }
                leaf v4RtAdded2RM {
                  type uint32;
                  config false;
                  description
                    "Number of IPv4 routes added to the routing table.";
                }
                leaf v4RtUnAdded2RM {
                  type uint32;
                  config false;
                  description
                    "Number of IPv4 Routes that are not added to the routing table.";
                }
                leaf v6RtAdded2RM {
                  type uint32;
                  config false;
                  description
                    "Number of IPv6 routes added to the routing table.";
                }
                leaf v6RtUnAdded2RM {
                  type uint32;
                  config false;
                  description
                    "Number of IPv6 Routes that are not added to the routing table.";
                }
              }
            }
            container isDispV4Routes {
              config false;
              description
                "List of routing information.";
              list isDispV4Route {
                key "levelType ipv4Address ipv4Mask nextHop";
                config false;
                description
                  "IS-IS routing information.";
                leaf levelType {
                  type isiscommLevelType;
                  config false;
                  description
                    "Level type, which can be level-1 or level-2. ";
                }
                leaf ipv4Address {
                  type string {
                    length "0..20";
                  }
                  config false;
                  description
                    "IPv4 address prefix.";
                }
                leaf ipv4Mask {
                  type uint32;
                  config false;
                  description
                    "IPv4 address mask.";
                }
                leaf intCost {
                  type uint32;
                  config false;
                  description
                    "Internal cost value of IPv4 routes.";
                }
                leaf extCost {
                  type string {
                    length "0..8";
                  }
                  config false;
                  description
                    "External cost value of IPv4 routes.";
                }
                leaf exitInterfaceName {
                  type string {
                    length "0..64";
                  }
                  config false;
                  description
                    "Outbound interface name of a route.";
                }
                leaf nextHop {
                  type string {
                    length "0..20";
                  }
                  config false;
                  description
                    "Next hop of a route.";
                }
                leaf flags {
                  type string {
                    length "0..12";
                  }
                  config false;
                  description
                    "Route Flags: 
D: Direct
A: Added to URT
L: Advertised in LSPs
S: IGP Shortcut
U: Up/Down Bit Set";
                }
                leaf priority {
                  type string {
                    length "0..31";
                  }
                  config false;
                  description
                    "Route priority: Critical, High, Medium, or Low.";
                }
                leaf tag {
                  type string {
                    length "0..31";
                  }
                  config false;
                  description
                    "Tag of a route.";
                }
              }
            }
            container isDispV6Routes {
              config false;
              description
                "List of the information about IPv6 routes.";
              list isDispV6Route {
                key "levelType ipv6Address ipv6Mask nextHop";
                config false;
                description
                  "Information about IPv6 routes.";
                leaf levelType {
                  type isiscommLevelType;
                  config false;
                  description
                    "Level type: level-1 or level-2. ";
                }
                leaf ipv6Address {
                  type string {
                    length "0..60";
                  }
                  config false;
                  description
                    "IPv6 address prefix of a route.";
                }
                leaf ipv6Mask {
                  type uint32;
                  config false;
                  description
                    "IPv6 address mask of a route.";
                }
                leaf exitInterfaceName {
                  type string {
                    length "0..64";
                  }
                  config false;
                  description
                    "Outbound interface name of a route.";
                }
                leaf nextHop {
                  type string {
                    length "0..60";
                  }
                  config false;
                  description
                    "Next hop of a route.";
                }
                leaf costValue {
                  type uint32;
                  config false;
                  description
                    "Cost value of IPv6 routes.";
                }
                leaf flags {
                  type string {
                    length "0..12";
                  }
                  config false;
                  description
                    "Route type.";
                }
                leaf priority {
                  type string {
                    length "0..31";
                  }
                  config false;
                  description
                    "Route priority: Critical, High, Medium, or Low.";
                }
                leaf tag {
                  type string {
                    length "0..31";
                  }
                  config false;
                  description
                    "Tag of a route.";
                }
              }
            }
            container isDispV4ImportRoutes {
              config false;
              description
                "List of the information about the imported IPv4 routes.";
              list isDispV4ImportRoute {
                key "levelType routeProtocolType ipv4Address ipv4Mask";
                config false;
                description
                  "Information about the imported IPv4 routes.";
                leaf levelType {
                  type isiscommLevelType;
                  config false;
                  description
                    "Level type: level-1 or level-2. ";
                }
                leaf routeProtocolType {
                  type string {
                    length "0..4";
                  }
                  config false;
                  description
                    "Protocol type of the imported routes.(S:STATIC, D:DIRECT, O:OSPF, B:BGP, I:ISIS, U:UNR, R:RIP)";
                }
                leaf ipv4Address {
                  type string {
                    length "0..20";
                  }
                  config false;
                  description
                    "IPv4 address prefix of the imported routes.";
                }
                leaf ipv4Mask {
                  type uint32;
                  config false;
                  description
                    "IPv4 mask of the imported routes.";
                }
                leaf intCost {
                  type uint32;
                  config false;
                  description
                    "IPv4 internal cost value of the imported routes.";
                }
                leaf extCost {
                  type string {
                    length "0..12";
                  }
                  config false;
                  description
                    "IPv4 external cost value of the imported routes.";
                }
                leaf tag {
                  type string {
                    length "0..12";
                  }
                  config false;
                  description
                    "Tag value of the imported routes.";
                }
              }
            }
            container isDispV6ImportRoutes {
              config false;
              description
                "List of the information about the imported IPv6 routes.";
              list isDispV6ImportRoute {
                key "levelType routeProtocolType ipv6Address ipv6Mask";
                config false;
                description
                  "Information about the imported IPv6 routes.";
                leaf levelType {
                  type isiscommLevelType;
                  config false;
                  description
                    "Level type: level-1 or level-2. ";
                }
                leaf routeProtocolType {
                  type string {
                    length "0..4";
                  }
                  config false;
                  description
                    "Protocol type of the imported routes.";
                }
                leaf ipv6Address {
                  type string {
                    length "0..60";
                  }
                  config false;
                  description
                    "IPv6 address prefix of the imported routes.";
                }
                leaf ipv6Mask {
                  type uint32;
                  config false;
                  description
                    "IPv6 mask of the imported routes.";
                }
                leaf intCost {
                  type uint32;
                  config false;
                  description
                    "IPv6 internal cost value of the imported routes.";
                }
                leaf tag {
                  type string {
                    length "0..12";
                  }
                  config false;
                  description
                    "Tag value of the imported routes.";
                }
              }
            }
            container isDispMigpRoutes {
              config false;
              description
                "List of MIGP routing information.";
              list isDispMigpRoute {
                key "levelType ipv4Address ipv4Mask nextHop";
                config false;
                description
                  "MIGP routing information.";
                leaf levelType {
                  type isiscommLevelType;
                  config false;
                  description
                    "Level type: level-1 or level-2. ";
                }
                leaf ipv4Address {
                  type string {
                    length "0..20";
                  }
                  config false;
                  description
                    "IPv4 address prefix of a route.";
                }
                leaf ipv4Mask {
                  type uint32;
                  config false;
                  description
                    "IPv4 address mask of a route.";
                }
                leaf intCost {
                  type uint32;
                  config false;
                  description
                    "Internal cost value of IPv4 routes.";
                }
                leaf extCost {
                  type string {
                    length "0..8";
                  }
                  config false;
                  description
                    "External cost value of IPv4 routes.";
                }
                leaf exitInterfaceName {
                  type string {
                    length "0..64";
                  }
                  config false;
                  description
                    "Outbound interface name of a route.";
                }
                leaf nextHop {
                  type string {
                    length "0..20";
                  }
                  config false;
                  description
                    "Next hop of a route.";
                }
                leaf flags {
                  type string {
                    length "0..12";
                  }
                  config false;
                  description
                    "Route Flags: 
A: Added to URT
U: Up/Down Bit Set";
                }
              }
            }
            container isLinkGroupPorts {
              description
                "Lists of Link-group Interface";
              list isLinkGroupPort {
                key "ifName linkgroupName linkGrouplevelType";
                description
                  "To set Link-group Interface.";
                leaf ifName {
                  type leafref {
                    path "/ifm:ifm/ifm:interfaces/ifm:interface/ifm:ifName";
                  }
                  description
                    "Interface name.";
                }
                leaf linkgroupName {
                  type string {
                    length "0..32";
                    pattern '.*\S.*';
                  }
                  description
                    "To set Link-group Name";
                  ext:allowDelete "true";
                }
                leaf linkGrouplevelType {
                  type isiscommLevelTypeWithTwo;
                  description
                    "Level type. The available options are level-1 and level-2. ";
                }
              }
            }
            container isSrLspTrig {
              when "../mtId=0";
              description
                "Run the sr-lsp-trig command.";
              leaf srLspTrigType {
                when "../../mtId=0";
                type isiscommsrLspTrigType;
                default "no_set";
                description
                  "Set the SR LSP trigger type.";
                ext:allowDelete "true";
              }
              leaf ipPrefixName {
                when "../../mtId=0";
                type string {
                  length "1..169";
                  pattern '.*\S.*';
                }
                must "../srLspTrigType='ipPrefix' or (not(../srLspTrigType='ipPrefix') and not(../ipPrefixName))";
                description
                  "Set the IP prefix name.";
                ext:allowDelete "true";
              }
            }
          }
        }
        container isDispLsdbs {
          config false;
          description
            "List of LSDB information.";
          list isDispLsdb {
            key "lspLevelType lspId";
            config false;
            description
              "Information about the LSDB.";
            leaf lspLevelType {
              type isiscommLevelType;
              config false;
              description
                "Level type: level-1 or level-2. ";
            }
            leaf lspId {
              type string {
                length "0..512";
              }
              config false;
              description
                "ID of an LSP.";
            }
            leaf seqenceNumber {
              type string {
                length "0..16";
              }
              config false;
              description
                "Serial number of an LSP.";
            }
            leaf checkSum {
              type string {
                length "0..16";
              }
              config false;
              description
                "Checksum of an LSP.";
            }
            leaf lspLength {
              type uint32 {
                range "0..2000";
              }
              config false;
              description
                "Length of an LSP.";
            }
            leaf attBit {
              type uint32 {
                range "0..1";
              }
              config false;
              description
                "ATT flag of an LSP.";
            }
            leaf partitionBit {
              type uint32 {
                range "0..1";
              }
              config false;
              description
                "Split flag of an LSP.";
            }
            leaf overloadBit {
              type uint32 {
                range "0..1";
              }
              config false;
              description
                "Overload flag of an LSP.";
            }
            leaf holdTime {
              type string {
                length "0..16";
              }
              config false;
              description
                "Holdtime of an LSP.";
            }
            leaf isLocalLsp {
              type boolean;
              config false;
              description
                "Local LSP flag.";
            }
          }
        }
        container isDispPeers {
          config false;
          description
            "List of neighbor information.";
          list isDispPeer {
            key "instanceId hostName levelType circuitId";
            config false;
            description
              "IS-IS neighbor information.";
            leaf instanceId {
              type uint32 {
                range "1..4294967295";
              }
              config false;
              description
                "Process ID of IS-IS instance to which the neighbor belongs.";
            }
            leaf hostName {
              type string {
                length "0..256";
              }
              config false;
              description
                "System name of a neighbor.";
            }
            leaf levelType {
              type isiscommLevelType;
              config false;
              description
                "Level type of a neighbor: level-1, level-2, or level-1-2. ";
            }
            leaf interfaceName {
              type string {
                length "0..64";
              }
              config false;
              description
                "Interface name of a neighbor.";
            }
            leaf circuitId {
              type string {
                length "0..260";
              }
              config false;
              description
                "Interface ID of a neighbor.";
            }
            leaf status {
              type isiscommAdjStatus;
              config false;
              description
                "Status of a neighbor.";
            }
            leaf holdTime {
              type uint32;
              config false;
              description
                "Holdtime of a neighbor.";
            }
            leaf priority {
              type string {
                length "0..4";
              }
              config false;
              description
                "Priority of a neighbor.";
            }
            leaf areaAddress {
              type string {
                length "0..120";
              }
              config false;
              description
                "Area address or a neighbor.";
            }
          }
        }
        container isDispCircs {
          config false;
          description
            "List of circuit information.";
          list isDispCirc {
            key "ifName";
            config false;
            description
              "IS-IS circuit information.";
            leaf ifName {
              type string {
                length "0..64";
              }
              config false;
              description
                "Name of the circuit.";
            }
            leaf ipv4L1Cost {
              type uint32 {
                range "0..16777215";
              }
              config false;
              description
                "Level1 Cost Of Ipv4.";
            }
            leaf ipv4L2Cost {
              type uint32 {
                range "0..16777215";
              }
              config false;
              description
                "Level2 Cost Of Ipv4.";
            }
            leaf ipv6L1Cost {
              type uint32 {
                range "0..16777215";
              }
              config false;
              description
                "Level1 Cost Of Ipv6.";
            }
            leaf ipv6L2Cost {
              type uint32 {
                range "0..16777215";
              }
              config false;
              description
                "Level2 Cost Of Ipv6.";
            }
          }
        }
        container isDispLspStatisticss {
          config false;
          description
            "List of LSP statistics.";
          list isDispLspStatistics {
            key "levelType systemId";
            config false;
            description
              "LSP statistics (local LSP statistics in an IS-IS process). ";
            leaf levelType {
              type isiscommLevelType;
              config false;
              description
                "Level type: level-1 or level-2. ";
            }
            leaf systemId {
              type string {
                length "0..16";
              }
              config false;
              description
                "System ID.";
            }
            leaf usedFragsNumber {
              type uint32;
              config false;
              description
                "Number of fragments.";
            }
          }
        }
        container isDispBfdSessions {
          config false;
          description
            "List of BFD session information.";
          list isDispBfdSession {
            key "peerLevelType peerIpAddress localIpAddress";
            config false;
            description
              "Information about a BFD session.";
            leaf peerLevelType {
              type isiscommLevelType;
              config false;
              description
                "Level type of the neighbor: level-1 or level-2. ";
            }
            leaf bfdState {
              type isiscommBfdStateType;
              config false;
              description
                "BFD status of a session.";
            }
            leaf bfdMinTx {
              type uint32;
              config false;
              description
                "Minimum interval at which BFD packets are sent after negotiation.";
            }
            leaf bfdMinRx {
              type uint32;
              config false;
              description
                "Minimum interval at which BFD packets are received after negotiation.";
            }
            leaf bfdMulNumber {
              type uint32;
              config false;
              description
                "Remote BFD detection multiplier.";
            }
            leaf peerIpAddress {
              type inet:ipv4-address-no-zone;
              config false;
              description
                "IP address of the neighbor interface.";
            }
            leaf localIpAddress {
              type inet:ipv4-address-no-zone;
              config false;
              description
                "IP address of the local interface.";
            }
            leaf systemId {
              type string {
                length "0..16";
              }
              config false;
              description
                "System ID of the neighbor.";
            }
            leaf circuitName {
              type string {
                length "0..64";
              }
              config false;
              description
                "Interface name.";
            }
          }
        }
        container isDispNameTables {
          config false;
          description
            "Name mapping table.";
          list isDispNameTable {
            key "levelType hostType systemId";
            config false;
            description
              "Name mapping table.";
            leaf levelType {
              type isiscommLevelType;
              config false;
              description
                "Type of the system level: level-1 or level-2. ";
            }
            leaf hostType {
              type isiscommIsHostType;
              config false;
              description
                "Type of the mapping between the system ID and host name.";
            }
            leaf hostName {
              type string {
                length "0..256";
              }
              config false;
              description
                "Host name (alias) mapped to the IS-IS system.";
            }
            leaf systemId {
              type string {
                length "0..32";
              }
              config false;
              description
                "IS-IS system ID or pseudo node ID to be mapped. ";
            }
          }
        }
        container isLinkGroups {
          description
            "List of link group";
          list isLinkGroup {
            key "groupName";
            description
              "Information about link group.";
            leaf groupName {
              type string {
                length "1..32";
                pattern '.*\S.*';
              }
              description
                "Group Name.";
            }
            leaf minMembers {
              type uint8 {
                range "2..64";
              }
              default "2";
              description
                "Min members of link group";
            }
            leaf revertMembers {
              type uint8 {
                range "2..64";
              }
              default "2";
              description
                "Members of revert cost";
            }
            leaf costOffset {
              type uint32 {
                range "1..16777215";
              }
              default "1";
              description
                "OffSet of cost.";
            }
          }
        }
        container isAvoidMicroLoopSet {
          description
            "Enable IS-IS avoid-microloop.";
          leaf frrAvoidLoopDisable {
            type boolean;
            default "true";
            description
              "Disable FRR avoid-microloop.";
            ext:allowDelete "false";
          }
          leaf ribUpdateDelayValue {
            type uint32 {
              range "100..5000";
            }
            default "100";
            description
              "Set the route delivery delay for FRR avoid-microloop. The default value is 100 ms.";
            ext:allowDelete "false";
          }
        }
        container isDispVirtualAccs {
          config false;
          description
            "Display the virtual access information list.";
          list isDispVirtualAcc {
            key "lspLevelType dispLspID";
            config false;
            description
              "Display the virtual access information.";
            leaf lspLevelType {
              type isiscommLevelType;
              config false;
              description
                "Display the level type.";
            }
            leaf dispLspID {
              type string {
                length "0..512";
              }
              config false;
              description
                "Display the LSP ID.";
            }
            leaf routerID {
              type inet:ipv4-address-no-zone;
              config false;
              description
                "Display the router ID.";
            }
            leaf apID {
              type inet:ipv4-address-no-zone;
              config false;
              description
                "Display the AP ID.";
            }
            leaf apRole {
              type string {
                length "0..16";
              }
              config false;
              description
                "Display the AP role.";
            }
          }
        }
      }
    }
    container isisGlobalCfg {
      description
        "ISIS Global Config";
      leaf lspSeqOverAutoRvFlag {
        type boolean;
        default "true";
        description
          "If enable, to recover ISIS system-id automatically when the sequence number of the local lsp overflowed";
      }
      leaf sysIdConflictAutoRvFlag {
        type boolean;
        default "true";
        description
          "If enable, to recover ISIS system-id automatically when the system-id conflicted";
      }
    }
  }
}
