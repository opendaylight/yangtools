/*
Copyright (C) 2013-2017 Huawei Technologies Co., Ltd. All rights reserved.
*/
submodule huawei-rsa-type {
  belongs-to huawei-rsa {
    prefix rsa;
  }
  
  organization
    "Huawei Technologies Co.,Ltd.";
  contact
    "Huawei Industrial Base Bantian, Longgang Shenzhen 518129                    
        People's Republic of China                    
        Website: http://www.huawei.com Email: support@huawei.com";
  description
    "Description of rsa type submodule";
  revision 2017-03-23 {
    description
      "Functions supported by the schema are added to the YANG file.";
    reference
      "Huawei private.";
  }
  revision 2013-01-01 {
    description
      "Init revision";
    reference
      "Huawei private.";
  }
  typedef rsaEncodeInType {
    type enumeration {
      enum "DER" {
        description
          "DER";
      }
      enum "PEM" {
        description
          "PEM";
      }
      enum "OPENSSH" {
        description
          "OPENSSH";
      }
    }
    description
      "RSA encodein type list";
  }
}
