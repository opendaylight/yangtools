/*
Copyright (C) 2013-2017 Huawei Technologies Co., Ltd. All rights reserved.
*/
submodule huawei-hwtacacs-action {
  belongs-to huawei-hwtacacs {
    prefix hwtacacs;
  }
  include huawei-hwtacacs-type;
  
  organization
    "Huawei Technologies Co.,Ltd.";
  contact
    "Huawei Industrial Base Bantian, Longgang Shenzhen 518129                    
        People's Republic of China                    
        Website: http://www.huawei.com Email: support@huawei.com";
  description
    "Description of hwtacacs action submodule";
  revision 2017-03-23 {
    description
      "Functions supported by the schema are added to the YANG file.";
    reference
      "Huawei private.";
  }
  revision 2013-01-01 {
    description
      "Init revision";
    reference
      "Huawei private.";
  }
  rpc hwTacRstAllStats {
    description
      "Reset All Statistics.";
  }
  rpc hwTacRstAuthenStats {
    description
      "Reset authentication statistics of the HWTACACS server.";
  }
  rpc hwTacRstAuthorStats {
    description
      "Reset authorization statistics of the HWTACACS server.";
  }
  rpc hwTacRstAccountStats {
    description
      "Reset accounting statistics of the HWTACACS server.";
  }
  rpc hwTacRstCommonStats {
    description
      "Reset common statistics of the HWTACACS server.";
  }
}
