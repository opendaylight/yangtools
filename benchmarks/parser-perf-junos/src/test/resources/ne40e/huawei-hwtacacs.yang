/*
Copyright (C) 2013-2017 Huawei Technologies Co., Ltd. All rights reserved.
*/
module huawei-hwtacacs {
  namespace "http://www.huawei.com/netconf/vrp/huawei-hwtacacs";
  prefix hwtacacs;
  import huawei-pub-type {
    prefix pub-type;
  }
  import huawei-l3vpn {
    prefix l3vpn;
  }
  import ietf-inet-types {
    prefix inet;
  }
  import huawei-extension {
    prefix ext;
  }
  include huawei-hwtacacs-action;
  include huawei-hwtacacs-type;
  
  organization
    "Huawei Technologies Co.,Ltd.";
  contact
    "Huawei Industrial Base Bantian, Longgang Shenzhen 518129                    
        People's Republic of China                    
        Website: http://www.huawei.com Email: support@huawei.com";
  description
    "Huawei Terminal Access Controller Access-Control System.";
  revision 2017-03-23 {
    description
      "Functions supported by the schema are added to the YANG file.";
    reference
      "Huawei private.";
  }
  revision 2013-01-01 {
    description
      "Init revision";
    reference
      "Huawei private.";
  }
  container hwtacacs {
    description
      "Huawei Terminal Access Controller Access-Control System.";
    container hwTacGlobalCfg {
      description
        "HWTACACS global configuration.";
      leaf isEnable {
        type boolean;
        default "false";
        description
          "Whether the HWTACACS server is enabled.";
        ext:allowDelete "true";
      }
      leaf totalTemplateNo {
        type uint32;
        config false;
        description
          "Total number of HWTACACS templates configured.";
      }
      leaf totalSrvNo {
        type uint32;
        config false;
        description
          "Total number of HWTACACS servers configured.";
      }
      leaf serviceName {
        type string {
          length "1..32";
        }
        description
          "HWTACACS service name.";
        ext:allowDelete "true";
      }
    }
    container hwTacTempCfgs {
      description
        "A set of HWTACACS templates.";
      list hwTacTempCfg {
        key "templateName";
        description
          "HWTACACS template.";
        leaf templateName {
          type string {
            length "1..32";
          }
          description
            "Name of a HWTACACS template, it is not case sensitive. The template name can have alphabets a to z (case insensitive) and numbers from 0 to 9 or symbols ('.', '-' and '_').";
        }
        leaf isDomainInclude {
          type boolean;
          default "true";
          description
            "Whether a domain name is included in a user name. By default, a user name contains the domain name.";
          ext:allowDelete "true";
        }
        leaf responseTimeout {
          type uint32 {
            range "1..300";
          }
          default "5";
          description
            "Server response timeout period. The default timeout period is 5 seconds.";
          ext:allowDelete "true";
        }
        leaf quietTime {
          type uint32 {
            range "1..255";
          }
          default "5";
          description
            "Time period after which the primary server restores to active. The default time period is 5 minutes. The time period can be modified no matter whether users are using the HWTACACS template.";
          ext:allowDelete "true";
        }
        leaf sharedKey {
          type pub-type:passwordExtend {
            length "1..255";
          }
          description
            "Shared key for a HWTACACS server. Configuring a shared key improves the communication security between a router and HWTACACS server. By default, no shared key is configured.";
          ext:allowDelete "true";
        }
        leaf sourceIpAddress {
          type inet:ipv4-address-no-zone;
          description
            "Source IP address for a HWTACACS server.";
          ext:allowDelete "true";
        }
        leaf domainMode {
          type hwtacacsDomainInclude;
          default "YES";
          description
            "To configure domain Mode";
          ext:allowDelete "true";
        }
        leaf priAuthenSrv {
          type inet:ipv4-address-no-zone;
          config false;
          description
            "IP address of the primary authentication server.";
        }
        leaf priCommonSrv {
          type inet:ipv4-address-no-zone;
          config false;
          description
            "IP address of the primary common server.";
        }
        leaf priAuthorSrv {
          type inet:ipv4-address-no-zone;
          config false;
          description
            "IP address of the primary authorization server.";
        }
        leaf curAuthenSrv {
          type inet:ipv4-address-no-zone;
          config false;
          description
            "IP address of the authentication server being used.";
        }
        leaf curAuthorSrv {
          type inet:ipv4-address-no-zone;
          config false;
          description
            "IP address of authorization server being used.";
        }
        leaf secAuthenSrvNo {
          type uint32;
          config false;
          description
            "Total number of configured secondary authentication servers in the template.";
        }
        leaf secCommonSrvNo {
          type uint32;
          config false;
          description
            "Total number of configured secondary common servers in the template.";
        }
        leaf secAuthorSrvNo {
          type uint32;
          config false;
          description
            "Total number of configured secondary authorization servers in the template.";
        }
        leaf priAuthenPort {
          type uint32;
          config false;
          description
            "Port of the primary authentication server.";
        }
        leaf priCommonPort {
          type uint32;
          config false;
          description
            "Port of the primary common server.";
        }
        leaf priAuthorPort {
          type uint32;
          config false;
          description
            "Port of the primary authorization server.";
        }
        leaf curAuthenPort {
          type uint32;
          config false;
          description
            "Authentication server port being used.";
        }
        leaf curAuthorPort {
          type uint32;
          config false;
          description
            "Authorization server port being used.";
        }
        leaf authenSrvOpenNo {
          type uint32;
          config false;
          description
            "Number of times that the HWTACACS client connected to the authentication server.";
        }
        leaf authenSrvClseNo {
          type uint32;
          config false;
          description
            "Number of times that the HWTACACS client disconnected from the authentication server.";
        }
        leaf authenReqNo {
          type uint32;
          config false;
          description
            "Number of authentication requests. ";
        }
        leaf authenRspNo {
          type uint32;
          config false;
          description
            "Number of authentication responses.";
        }
        leaf authenUnknownNo {
          type uint32;
          config false;
          description
            "Number of unknown authentication packets received by the HWTACACS client.";
        }
        leaf authenTimeoutNo {
          type uint32;
          config false;
          description
            "Number of times that authentication times out.";
        }
        leaf authenPktDropNo {
          type uint32;
          config false;
          description
            "Number of times that authentication packets are dropped.";
        }
        leaf authenChPassNo {
          type uint32;
          config false;
          description
            "Number of times that the password is changed for authentication.";
        }
        leaf authenLoginNo {
          type uint32;
          config false;
          description
            "Number of authentication logins.";
        }
        leaf authenSendNo {
          type uint32;
          config false;
          description
            "Number of authentication requests sent to server.";
        }
        leaf authenSndPassNo {
          type uint32;
          config false;
          description
            "Number of authentication password requests sent to the server.";
        }
        leaf authenAbortNo {
          type uint32;
          config false;
          description
            "Number of authentication abort requests sent to server.";
        }
        leaf authenConnectNo {
          type uint32;
          config false;
          description
            "Number of authentication connection requests sent to server.";
        }
        leaf authenRspErrNo {
          type uint32;
          config false;
          description
            "Number of authentication error responses received from server.";
        }
        leaf authenRspFailNo {
          type uint32;
          config false;
          description
            "Number of authentication response failures received from server.";
        }
        leaf authenFollowNo {
          type uint32;
          config false;
          description
            "Number of authentication Follow responses received from server.";
        }
        leaf authenGetdataNo {
          type uint32;
          config false;
          description
            "Number of authentication date responses received from server.";
        }
        leaf authenGetpassNo {
          type uint32;
          config false;
          description
            "Number of authentication password responses received from server.";
        }
        leaf authenGetusrNo {
          type uint32;
          config false;
          description
            "Number of authentication user responses received from server.";
        }
        leaf authenRspPassNo {
          type uint32;
          config false;
          description
            "Number of authentication-pass responses received from server.";
        }
        leaf authenRestartNo {
          type uint32;
          config false;
          description
            "Number of authentication-restart responses received from server.";
        }
        leaf authenPndreqNo {
          type uint32;
          config false;
          description
            "Number of authentication requests that are not processed.";
        }
        leaf authenRndTrpTim {
          type uint32;
          config false;
          description
            "Time (in tick) taken to complete the authentication.";
        }
        leaf authenMalformNo {
          type uint32;
          config false;
          description
            "Number of authentication errors.";
        }
        leaf authorSrvOpenNo {
          type uint32;
          config false;
          description
            "Number of times that the HWTACACS client connected to the authorization server.";
        }
        leaf authorSrvClseNo {
          type uint32;
          config false;
          description
            "Number of times that the HWTACACS client disconnected from the authorization server.";
        }
        leaf authorReqNo {
          type uint32;
          config false;
          description
            "Number of authorization requests. ";
        }
        leaf authorRspNo {
          type uint32;
          config false;
          description
            "Number of authorization responses.";
        }
        leaf authorUnknownNo {
          type uint32;
          config false;
          description
            "Number of unknown authorization packets received by HWTACACS client.";
        }
        leaf authorTimeoutNo {
          type uint32;
          config false;
          description
            "Number of times that authorization times out.";
        }
        leaf authorPktDropNo {
          type uint32;
          config false;
          description
            "Number of times that authorization packets are dropped.";
        }
        leaf authorEXECNo {
          type uint32;
          config false;
          description
            "Number of authorization requests for EXEC.";
        }
        leaf authorPPPNo {
          type uint32;
          config false;
          description
            "Number of authorization requests for PPP.";
        }
        leaf authorVPDNNo {
          type uint32;
          config false;
          description
            "Number of authorization requests for VPDN.";
        }
        leaf authorRspErrNo {
          type uint32;
          config false;
          description
            "Number of authorization error responses.";
        }
        leaf authorRspEXECNo {
          type uint32;
          config false;
          description
            "Number of authorization EXEC responses.";
        }
        leaf authorRspPPPNo {
          type uint32;
          config false;
          description
            "Number of authorization PPP responses.";
        }
        leaf authorRspVPDNNo {
          type uint32;
          config false;
          description
            "Number of authorization VPDN responses.";
        }
        leaf authorRndTrpTim {
          type uint32;
          config false;
          description
            "Time (in tick) taken to complete authorization.";
        }
        leaf authorPndreqNo {
          type uint32;
          config false;
          description
            "Number of authorization requests that are not processed.";
        }
        leaf authorMalformNo {
          type uint32;
          config false;
          description
            "Number of authorization errors.";
        }
        leaf secAccountSrvNo {
          type uint32;
          config false;
          description
            "Number of secondary accounting servers in the template.";
        }
        leaf curAccountPort {
          type uint32;
          config false;
          description
            "Accounting server port being used.";
        }
        leaf priAccountPort {
          type uint32;
          config false;
          description
            "Port of the primary accounting server.";
        }
        leaf curAccountSrv {
          type inet:ipv4-address-no-zone;
          config false;
          description
            "Accounting server port being used.";
        }
        leaf priAccountSrv {
          type inet:ipv4-address-no-zone;
          config false;
          description
            "Primary accounting server.";
        }
        leaf acctStopPktNo {
          type uint32;
          config false;
          description
            "Number of responses to accounting-stop packets.";
        }
        leaf acctRspPassNo {
          type uint32;
          config false;
          description
            "Number of responses to accounting-pass packets.";
        }
        leaf acctRspNo {
          type uint32;
          config false;
          description
            "Number of responses to accounting requests.";
        }
        leaf acctSrvOpenNo {
          type uint32;
          config false;
          description
            "Number of times that the HWTACACS client connected to the accounting server.";
        }
        leaf acctStartPktNo {
          type uint32;
          config false;
          description
            "Number of responses to accounting-start packets.";
        }
        leaf acctReqNo {
          type uint32;
          config false;
          description
            "Number of accounting requests sent to the server.";
        }
        leaf acctSrvClseNo {
          type uint32;
          config false;
          description
            "Number of times that the HWTACACS client disconnected from the accounting server.";
        }
        leaf acctRspErrNo {
          type uint32;
          config false;
          description
            "Number of abnormal accounting responses received from the server.";
        }
        leaf acctFollowNo {
          type uint32;
          config false;
          description
            "Number of accounting Follow responses received from server.";
        }
        leaf acctPndreqNo {
          type uint32;
          config false;
          description
            "Number of accounting requests that are not processed.";
        }
        container hwTacSrvCfgs {
          description
            "A set of HWTACACS servers.";
          list hwTacSrvCfg {
            key "serverIpAddress serverType isSecondaryServer vpnName isPublicNet";
            max-elements  "32";
            description
              "HWTACACS IPV4 server. A maximum 32 servers can be configured in one template ";
            leaf serverIpAddress {
              type inet:ipv4-address-no-zone;
              description
                "Server IPv4 address. Must be a valid unicast IP address.";
            }
            leaf serverType {
              type hwtacacsSrvType;
              description
                "Server type: authentication/authorization/accounting/common.";
            }
            leaf isSecondaryServer {
              type boolean;
              description
                "Whether the server is secondary. By default, a server is a secondary server.";
            }
            leaf vpnName {
              type leafref {
                path "/l3vpn:l3vpn/l3vpn:l3vpncomm/l3vpn:l3vpnInstances/l3vpn:l3vpnInstance/l3vpn:vrfName";
              }
              description
                "VPN instance name.";
            }
            leaf isPublicNet {
              type boolean;
              description
                "Set the public-net.";
            }
            leaf serverPort {
              type uint32 {
                range "1..65535";
              }
              default "49";
              description
                "Server port. Value range: 1-65535. The default port number is 49.";
              ext:allowDelete "true";
            }
            leaf isMuxModeEnable {
              type boolean;
              default "false";
              description
                "Whether the MUX mode is enabled for the server. By default, the MUX mode is disabled.";
              ext:allowDelete "true";
            }
            leaf serverCurrentState {
              type hwtacacsSrvState;
              config false;
              description
                "Server running status.";
            }
            leaf isCurrentSrv {
              type boolean;
              default "false";
              config false;
              description
                "Whether the server is being used.";
            }
            leaf sharedKey {
              type pub-type:passwordExtend {
                length "1..255";
              }
              description
                "Shared key for a HWTACACS server. Configuring a shared key improves the communication security between a router and HWTACACS server. By default, no shared key is configured.";
              ext:allowDelete "true";
            }
            leaf authenSrvOpenNo {
              type uint32;
              config false;
              description
                "Number of times that the HWTACACS client connected to the authentication server.";
            }
            leaf authenSrvClseNo {
              type uint32;
              config false;
              description
                "Number of times that the HWTACACS client disconnected from the authentication server.";
            }
            leaf authenReqNo {
              type uint32;
              config false;
              description
                "Number of authentication requests. ";
            }
            leaf authenRspNo {
              type uint32;
              config false;
              description
                "Number of authentication responses.";
            }
            leaf authorSrvOpenNo {
              type uint32;
              config false;
              description
                "Number of times that the HWTACACS client connected to the authorization server.";
            }
            leaf authorSrvClseNo {
              type uint32;
              config false;
              description
                "Number of times that the HWTACACS client disconnected from the authorization server.";
            }
            leaf authorReqNo {
              type uint32;
              config false;
              description
                "Number of authorization requests. ";
            }
            leaf authorRspNo {
              type uint32;
              config false;
              description
                "Number of authorization responses.";
            }
            leaf acctReqNo {
              type uint32;
              config false;
              description
                "Number of accounting requests. ";
            }
            leaf acctRspNo {
              type uint32;
              config false;
              description
                "Number of accounting responses.";
            }
            leaf acctSrvOpenNo {
              type uint32;
              config false;
              description
                "Number of times that the HWTACACS client connected to the accounting server.";
            }
            leaf acctSrvClseNo {
              type uint32;
              config false;
              description
                "Number of times that the HWTACACS client disconnected from the accounting server.";
            }
          }
        }
        container hwTacIpv6SrvCfgs {
          description
            "A set of HWTACACS servers.";
          list hwTacIpv6SrvCfg {
            key "serverIpAddress serverType isSecondaryServer vpnName";
            max-elements  "32";
            description
              "HWTACACS IPV6 server. A maximum 32 servers can be configured in one template ";
            leaf serverIpAddress {
              type inet:ipv6-address-no-zone;
              description
                "Server IPv6 address. Must be a valid unicast IP address.";
            }
            leaf serverType {
              type hwtacacsSrvType;
              description
                "Server type: authentication/authorization/accounting/common.";
            }
            leaf isSecondaryServer {
              type boolean;
              description
                "Whether the server is secondary. By default, a server is a secondary server.";
            }
            leaf vpnName {
              type leafref {
                path "/l3vpn:l3vpn/l3vpn:l3vpncomm/l3vpn:l3vpnInstances/l3vpn:l3vpnInstance/l3vpn:vrfName";
              }
              description
                "Configure the vpn-instance name.";
            }
            leaf serverPort {
              type uint32 {
                range "1..65535";
              }
              default "49";
              description
                "Server port. Value range: 1-65535. The default port number is 49.";
              ext:allowDelete "true";
            }
            leaf isMuxModeEnable {
              type boolean;
              default "false";
              description
                "Whether the MUX mode is enabled for the server. By default, the MUX mode is disabled.";
              ext:allowDelete "true";
            }
            leaf serverCurrentState {
              type hwtacacsSrvState;
              config false;
              description
                "Server running status.";
            }
            leaf isCurrentSrv {
              type boolean;
              default "false";
              config false;
              description
                "Whether the server is being used.";
            }
            leaf sharedKey {
              type pub-type:passwordExtend {
                length "1..255";
              }
              description
                "Shared key for a HWTACACS server. Configuring a shared key improves the communication security between a router and HWTACACS server. By default, no shared key is configured.";
              ext:allowDelete "true";
            }
            leaf authenSrvOpenNo {
              type uint32;
              config false;
              description
                "Number of times that the HWTACACS client connected to the authentication server.";
            }
            leaf authenSrvClseNo {
              type uint32;
              config false;
              description
                "Number of times that the HWTACACS client disconnected from the authentication server.";
            }
            leaf authenReqNo {
              type uint32;
              config false;
              description
                "Number of authentication requests. ";
            }
            leaf authenRspNo {
              type uint32;
              config false;
              description
                "Number of authentication responses.";
            }
            leaf authorSrvOpenNo {
              type uint32;
              config false;
              description
                "Number of times that the HWTACACS client connected to the authorization server.";
            }
            leaf authorSrvClseNo {
              type uint32;
              config false;
              description
                "Number of times that the HWTACACS client disconnected from the authorization server.";
            }
            leaf authorReqNo {
              type uint32;
              config false;
              description
                "Number of authorization requests. ";
            }
            leaf authorRspNo {
              type uint32;
              config false;
              description
                "Number of authorization responses.";
            }
            leaf acctReqNo {
              type uint32;
              config false;
              description
                "Number of accounting requests. ";
            }
            leaf acctRspNo {
              type uint32;
              config false;
              description
                "Number of accounting responses.";
            }
            leaf acctSrvOpenNo {
              type uint32;
              config false;
              description
                "Number of times that the HWTACACS client connected to the accounting server.";
            }
            leaf acctSrvClseNo {
              type uint32;
              config false;
              description
                "Number of times that the HWTACACS client disconnected from the accounting server.";
            }
          }
        }
        container hwTacHostSrvCfgs {
          description
            "A set of HWTACACS servers.";
          list hwTacHostSrvCfg {
            key "serverHostName serverType isSecondaryServer vpnName isPublicNet";
            max-elements  "32";
            description
              "HWTACACS Host server. A maximum 32 servers can be configured in one template.";
            leaf serverHostName {
              type string {
                length "1..255";
              }
              description
                "Host name of HWTACACS server. Host name, Can include character '.', '-', '_' and lowercase or uppercase letters and digit, at least include one letter or digit.";
            }
            leaf serverType {
              type hwtacacsSrvType;
              description
                "Server type: authentication/authorization/accounting/common.";
            }
            leaf isSecondaryServer {
              type boolean;
              description
                "Whether the server is secondary. By default, a server is a secondary server.";
            }
            leaf vpnName {
              type leafref {
                path "/l3vpn:l3vpn/l3vpn:l3vpncomm/l3vpn:l3vpnInstances/l3vpn:l3vpnInstance/l3vpn:vrfName";
              }
              description
                "VPN instance name.";
            }
            leaf isPublicNet {
              type boolean;
              description
                "Set the public-net.";
            }
            leaf serverPort {
              type uint32 {
                range "1..65535";
              }
              default "49";
              description
                "Server port. Value range: 1-65535. The default port number is 49.";
              ext:allowDelete "true";
            }
            leaf isMuxModeEnable {
              type boolean;
              default "false";
              description
                "Whether the MUX mode is enabled for the server. By default, the MUX mode is disabled.";
              ext:allowDelete "true";
            }
            leaf serverCurrentState {
              type hwtacacsSrvState;
              config false;
              description
                "Server running status.";
            }
            leaf isCurrentSrv {
              type boolean;
              default "false";
              config false;
              description
                "Whether the server is being used.";
            }
            leaf sharedKey {
              type pub-type:passwordExtend {
                length "1..255";
              }
              description
                "Shared key for a HWTACACS server. Configuring a shared key improves the communication security between a router and HWTACACS server. By default, no shared key is configured.";
              ext:allowDelete "true";
            }
            leaf authenSrvOpenNo {
              type uint32;
              config false;
              description
                "Number of times that the HWTACACS client connected to the authentication server.";
            }
            leaf authenSrvClseNo {
              type uint32;
              config false;
              description
                "Number of times that the HWTACACS client disconnected from the authentication server.";
            }
            leaf authenReqNo {
              type uint32;
              config false;
              description
                "Number of authentication requests. ";
            }
            leaf authenRspNo {
              type uint32;
              config false;
              description
                "Number of authentication responses.";
            }
            leaf authorSrvOpenNo {
              type uint32;
              config false;
              description
                "Number of times that the HWTACACS client connected to the authorization server.";
            }
            leaf authorSrvClseNo {
              type uint32;
              config false;
              description
                "Number of times that the HWTACACS client disconnected from the authorization server.";
            }
            leaf authorReqNo {
              type uint32;
              config false;
              description
                "Number of authorization requests. ";
            }
            leaf authorRspNo {
              type uint32;
              config false;
              description
                "Number of authorization responses.";
            }
            leaf acctReqNo {
              type uint32;
              config false;
              description
                "Number of accounting requests. ";
            }
            leaf acctRspNo {
              type uint32;
              config false;
              description
                "Number of accounting responses.";
            }
            leaf acctSrvOpenNo {
              type uint32;
              config false;
              description
                "Number of times that the HWTACACS client connected to the accounting server.";
            }
            leaf acctSrvClseNo {
              type uint32;
              config false;
              description
                "Number of times that the HWTACACS client disconnected from the accounting server.";
            }
          }
        }
      }
    }
  }
}
