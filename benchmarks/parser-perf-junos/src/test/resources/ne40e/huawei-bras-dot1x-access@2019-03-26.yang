/*
Copyright (C) 2019 Huawei Technologies Co., Ltd. All rights reserved.
*/
module huawei-bras-dot1x-access {
  namespace "urn:huawei:yang:huawei-bras-dot1x-access";
  prefix bras-dot1x-access;
  import huawei-ifm {
    prefix ifm;
  }
  import huawei-bras-basic-access {
    prefix bras-basic-access;
  }
  import huawei-extension {
    prefix ext;
  }
  ext:task-name "bas-eap";
  organization
    "Huawei Technologies Co., Ltd.";
  contact
    "Huawei Industrial Base
     Bantian, Longgang
     Shenzhen 518129
     People's Republic of China
     Website: http://www.huawei.com
     Email: support@huawei.com";
  description
    "Configure the dot1x access.";
  revision 2019-03-26 {
    description
      "Initial revision.";
    reference
      "Huawei private.";
  }

  container bras-dot1x-access {
    description
      "Dot1x access.";
    container dot1x-templates {
      description
        "List of dot1x templates. Has default record dot1x-template index 1.";
      list dot1x-template {
        key "index";
        max-elements "256";
        description
          "Configure dot1x template.";
        ext:generated-by system {
          ext:filter "index=1";
          description "The instance whose index is 1 is generated by system automatically.";
        }
        ext:operation-exclude create|delete {
          ext:filter "index=1";
          description "The instance whose index is 1 cannot be created or deleted.";
        }
        leaf index {
          type uint16 {
            range "1..256";
          }
          description
            "Dot1x template index.";
        }
        leaf re-authentication-interval {
          type uint32 {
            range "0..65535";
          }
          default "57600";
          description
            "Re-authentication interval time.";
        }
        leaf authentication-timeout {
          type uint16 {
            range "1..300";
          }
          default "30";
          description
            "Authentication timeout interval.";
        }
        leaf authentication-method {
          type enumeration {
            enum "chap" {
              value 0;
              description
                "CHAP encryption.";
            }
            enum "pap" {
              value 1;
              description
                "PAP encryption.";
            }
            enum "none" {
              value 2;
              description
                "EAP relay mode.";
            }
          }
          default "none";
          description
            "Dot1x authentication method.";
        }
        leaf keepalive-interval {
          type uint16 {
            range "1..1800";
          }
          default "20";
          description
            "KeepAlive interval.";
        }
        leaf keepalive-retransmit {
          type uint16 {
            range "0..10";
          }
          default "0";
          description
            "Number of KeepAlive retransmission times.";
        }
        leaf request-interval {
          type uint16 {
            range "1..300";
          }
          default "30";
          description
            "Interval for sending request packets.";
        }
        leaf request-retransmit {
          type uint16 {
            range "1..10";
          }
          default "2";
          description
            "Number of request retransmission times.";
        }
      }
    }
  }

  augment "/ifm:ifm/ifm:interfaces/ifm:interface/bras-basic-access:bas/bras-basic-access:access-type/bras-basic-access:layer2-subscriber/bras-basic-access:layer2-subscriber" {
    description
      "Configure the device to initiate EAP authentication.";
    container dot1x-trigger {
      leaf trigger-enable {
        type empty;
        description
          "Whether to enable the device to initiate EAP authentication.";
      }
      description
        "Configure the device to initiate EAP authentication. By default, the device is disabled from initiating EAP authentication.";
    }
  }
}
