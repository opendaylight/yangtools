module ietf-yang-metadata {

  namespace "urn:ietf:params:xml:ns:yang:ietf-yang-metadata";

  prefix "md";

  organization
    "IETF NETMOD (NETCONF Data Modeling Language) Working Group";

  contact
    "Editor:   Ladislav Lhotka
               <mailto:lhotka@nic.cz>";

  description
    "This YANG module defines an extension statement that allows for
     defining metadata annotations.";

  revision 2014-09-11 {
    description
      "Initial revision.";
    reference
      "RFC XXXX: Defining and Using Metadata with YANG";
  }

  extension annotation {
    argument name;
    description
      "This extension allows for defining metadata annotations in
       YANG modules. The 'md:annotation' statement can appear only at
       the top level of a YANG module.

       An annotation defined with this extension statement inherits
       the namespace and other context from the YANG module in which
       it is defined.

       Other properties of the annotation and documentation may be
       specified using the following standard YANG substatements (all
       are optional and may appear only once): 'type', 'description',
       'reference', 'status' and 'units'. If the 'type' statement is
       not present, the built-in 'string' type is used by default.

       A server announces support for a particular annotation by
       including the module in which the annotation is defined among
       the advertised YANG modules (e.g. in NETCONF hello message).
       Depending on the prescribed usage patterns, the annotation
       then may be attached by the server and/or client to any valid
       instance of a data node defined by the server's data model.

       XML and JSON encoding of annotations is defined in
       RFC XXXX.";
  }
}
