/*
Copyright (C) 2013-2017 Huawei Technologies Co., Ltd. All rights reserved.
*/
submodule huawei-l2tpv3-action {
  belongs-to huawei-l2tpv3 {
    prefix l2tpv3;
  }
  include huawei-l2tpv3-type;
  
  organization
    "Huawei Technologies Co.,Ltd.";
  contact
    "Huawei Industrial Base Bantian, Longgang Shenzhen 518129                    
        People's Republic of China                    
        Website: http://www.huawei.com Email: support@huawei.com";
  description
    "Description FOR submodule";
  revision 2017-03-23 {
	description
	"Functions supported by the schema are added to the YANG file.";
	reference
	"Huawei private.";
	}
  revision 2013-01-01 {
    description
      "Init revision";
    reference    "Huawei private.";
  }
  rpc resetStats {
    description
      "Reset the statistic result.";
    input {
      leaf pwName {
        type string {
          length "1..19";
        }
        description
          "Name of a Tunnel.";
      }
    }
  }
}
