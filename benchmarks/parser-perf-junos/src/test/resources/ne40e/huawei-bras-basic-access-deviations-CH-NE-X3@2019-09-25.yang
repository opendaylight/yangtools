/*
Copyright (C) 2019 Huawei Technologies Co., Ltd. All rights reserved.
*/
module huawei-bras-basic-access-deviations-CH-NE-X3 {
  namespace "urn:huawei:yang:huawei-bras-basic-access-deviations-CH-NE-X3";
  prefix bras-basic-access-devs-CH-NE-X3;

  import huawei-bras-basic-access {
    prefix bras-basic-access;
  }
  import huawei-devm {
    prefix devm;
  }
  organization
    "Huawei Technologies Co., Ltd.";
  contact
    "Huawei Industrial Base
     Bantian, Longgang
     Shenzhen 518129
     People's Republic of China
     Website: http://www.huawei.com
     Email: support@huawei.com";
  description
    "Global Configuration.";

  revision 2019-09-25 {
    description
      "Init revision.";
    reference "Huawei private.";
  }
  deviation /devm:devm/devm:mpu-boards/devm:mpu-board/bras-basic-access:bras {
    deviate not-supported;
  }
}
