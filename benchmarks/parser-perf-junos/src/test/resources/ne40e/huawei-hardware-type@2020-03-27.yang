/*
Copyright (C) 2020 Huawei Technologies Co., Ltd. All rights reserved.
*/
module huawei-hardware-type {
  namespace "urn:huawei:yang:huawei-hardware-type";
  prefix hardware-type;
  
  import huawei-extension {
    prefix ext;
  }

  organization
    "Huawei Technologies Co., Ltd.";
  contact
    "Huawei Industrial Base
     Bantian, Longgang
     Shenzhen 518129
     People's Republic of China
     Website: http://www.huawei.com
     Email: support@huawei.com";
  description
    "This YANG module define hardware datatypes.";
    
  revision 2020-03-27 {
    description
      "The modifications in the schema file are synchronized to the YANG file.";
    reference
      "Huawei private.";
  }
  ext:task-name "device-mgr";
  
  typedef hardware-entityclass-type {
    type enumeration {
      enum "other" {
        value 0;
        description
          "Other.";
      }
      enum "chassis" {
        value 1;
        description
          "Chassis.";
      }
      enum "container" {
        value 2;
        description
          "Container.";
      }
      enum "board" {
        value 3;
        description
          "Board.";
      }
      enum "mpu-module" {
        value 4;
        description
          "MPU.";
      }
      enum "lpu-module" {
        value 5;
        description
          "LPU.";
      }
      enum "sfu-module" {
        value 6;
        description
          "SFU.";
      }
      enum "clock-module" {
        value 7;
        description
          "CLK.";
      }
      enum "card" {
        value 8;
        description
          "Card.";
      }
      enum "flexiblecard-module" {
        value 9;
        description
          "Flexible card.";
      }
      enum "port" {
        value 10;
        description
          "Port.";
      }
      enum "fan" {
        value 16;
        description
          "Fan.";
      }
      enum "powersupply" {
        value 17;
        description
          "Power supply.";
      }
      enum "pp-module" {
        value 4108;
        description
          "PP Module.";
      }
      enum "swf-module" {
        value 4109;
        description
          "SWF Module.";
      }
      enum "ecu-module" {
        value 4110;
        description
          "ECU.";
      }
      enum "icu-module" {
        value 4111;
        description
          "ICU.";
      }
      enum "lfe" {
        value 4162;
        description
          "Lfe.";
      }
      enum "cf-module" {
        value 4170;
        description
          "CF card.";
      }
      enum "lcd" {
        value 4181;
        description
          "LCD.";
      }
      enum "cmu-module" {
        value 5010;
        description
          "CMU.";
      }
      enum "tsu" {
        value 5012;
        description
          "TSU.";
      }
      enum "pmu" {
        value 5031;
        description
          "PMU.";
      }
      enum "pm" {
        value 5032;
        description
          "PM.";
      }
      enum "pem" {
        value 5006;
        description
          "PEM.";
      }
      enum "pdu" {
        value 5086;
        description
          "PDU.";
      }
      enum "dmu" {
        value 5087;
        description
          "DMU.";
      }
      enum "dacs" {
        value 5088;
        description
          "DACS.";
      }
    }
    description
      "Physical entity class.";
  }
  
  typedef hardware-chassis-type {
    type enumeration {
      enum "unknown" {
        value 0;
        description
          "Unknown.";
      }
      enum "ATN950C" {
        value 1;
        description
          "ATN 950C chassis.";
      }
      enum "ATN910C-E" {
        value 2;
        description
         "ATN910C-E chassis.";
      }
      enum "ATN910C-A" {
        value 3;
        description
          "ATN 910C-A chassis.";
      }
      enum "ATN910C-B" {
        value 4;
        description
          "ATN 910C-B chassis.";
      }
      enum "ATN910C-D" {
        value 5;
        description
          "ATN910C-D chassis.";
      }
      enum "NE05E-SQ" {
        value 6;
        description
          "NE05E-SQ chassis.";
      }
      enum "NE08E-S6E" {
        value 7;
        description
          "NE08E-S6E chassis.";
      }
      enum "ATN980B-DC" {
        value 8;
        description
          "ATN 980B-DC chassis.";
      }
       enum "ATN980C" {
        value 9;
        description
          "ATN 980C chassis.";
      }
      enum "ATN980B-AC-A" {
        value 10;
        description
          "ATN 980B-AC-A chassis.";
      }
      enum "ATN980B-AC-B" {
        value 11;
        description
          "ATN 980B-AC-B chassis.";
      }
      enum "ATN980B-AC-C" {
        value 12;
        description
          "ATN 980B-AC-C chassis.";
      }
      enum "ATN950B" {
        value 13;
        description
          "ATN 950B chassis.";
      }
      enum "ATN910B" {
        value 14;
        description
          "ATN 910B chassis.";
      }
      enum "ATN910B-D" {
        value 15;
        description
          "ATN 910B-D chassis.";
      }
      enum "ATN910B-E" {
        value 16;
        description
          "ATN 910B-E chassis.";
      }
      enum "ATN910B-F" {
        value 17;
        description
          "ATN 910B-F chassis.";
      }
      enum "ATN905" {
        value 18;
        description
          "ATN905 chassis.";
      }
      enum "ETN500-F" {
        value 19;
        description
          "ETN500-F chassis.";
      }
      enum "NE05E-SR" {
        value 20;
        description
          "NE05E-SR chassis.";
      }
      enum "NE08E-S9" {
        value 21;
        description
          "NE08E-S9 chassis.";
      }
      enum "fname8090Unknown" {
        value 22;
        description
          "Unknown.";
      }
      enum "fname8090Whole" {
        value 23;
        description
          "NE5000E chassis.";
      }
      enum "fname8090NE5000EX16" {
        value 24;
        description
          "NE5000EX chassis.";
      }
      enum "fname8090ClusterCentral" {
        value 25;
        description
          "NE5000E cluster central chassis.";
      }
      enum "fname8090NE5000EX-VB" {
        value 26;
        description
          "NE5000EX-VB chassis.";
      }
      enum "fname8090NE5000EX16A" {
        value 27;
        description
          "NE5000EX16A Chassis.";
      }
      enum "fname8090NE5000EX16B" {
        value 28;
        description
          "NE5000EX16B Chassis.";
      }
      enum "fname8090NE40E-X16B" {
        value 29;
        description
          "NE40E-X16B Chassis.";
      }
      enum "fname8090NE5000ECCC-A" {
        value 30;
        description
          "NE5000ECCC-A Chassis.";
      }
      enum "CE685048S4QEI" {
        value 31;
        description
          "CE685048S4QEI chassis.";
      }
      enum "CE585048T4S2QEI" {
        value 32;
        description
          "CE585048T4S2QEI chassis.";
      }
      enum "CE685048T4QEI" {
        value 33;
        description
          "CE685048T4QEI chassis.";
      }
      enum "fname8090CX600-M8-AC" {
        value 34;
        description
          "CX600-M8-AC chassis.";
      }
      enum "fname8090CX600-M4" {
        value 35;
        description
          "CX600-M4 chassis.";
      }
      enum "fname8090CX600-M16" {
        value 36;
        description
          "CX600-M16 chassis.";
      }
      enum "fname8090CX600-X2-M8-AC" {
        value 37;
        description
          "CX600-X2-M8-AC chassis.";
      }
      enum "fname8031CX600-M2E" {
        value 38;
        description
          "CX600-M2E chassis.";
      }
      enum "fname8031CX600-M2F" {
        value 39;
        description
          "CX600-M2F chassis.";
      }
      enum "fname8090CX600-X1" {
        value 40;
        description
          "CX600-X1 chassis.";
      }
      enum "fname8090CX600-X2" {
        value 41;
        description
          "CX600-X2 chassis.";
      }
      enum "fname8090CX600-X1-M4" {
        value 42;
        description
          "CX600-X1-M4 chassis.";
      }
      enum "fname8090CX600-X2-M16" {
        value 43;
        description
          "CX600-X2-M16 chassis.";
      }
      enum "fname8090NE20E-X1" {
        value 44;
        description
          "NE20E-X1 chassis.";
      }
      enum "fname8090NE20E-X2" {
        value 45;
        description
          "NE20E-X2 chassis.";
      }
      enum "fname8090NE20E-X2-M8" {
        value 46;
        description
          "NE20E-X2-M8 chassis.";
      }
      enum "fname8090NE20E-X2-M16" {
        value 47;
        description
          "NE20E-X2-M16 chassis.";
      }
      enum "fnameNE20E-S2E" {
        value 48;
        description
          "NE20E-S2E chassis.";
      }
      enum "fnameNE20E-S2F" {
        value 49;
        description
          "NE20E-S2F chassis.";
      }
      enum "fname8090NE40E-X1" {
        value 50;
        description
          "NE40E-X1 chassis.";
      }
      enum "fname8090NE40E-X1-M4" {
        value 51;
        description
          "NE40E-X1-M4 chassis.";
      }
      enum "fname8090NE40E-X2" {
        value 52;
        description
          "NE40E-X2 chassis.";
      }
      enum "fname8090NE40E-M2E" {
        value 53;
        description
          "NE40E-M2E chassis.";
      }
      enum "fname8090NE40E-M2F" {
        value 54;
        description
          "NE40E-M2F chassis.";
      }
      enum "fname8090NE40E-X8" {
        value 55;
        description
          "NE40E-X8 chassis.";
      }
      enum "fname8090NE40E-X16" {
        value 56;
        description
          "NE40E-X16 chassis.";
      }
      enum "fname8090NE40E-X16A" {
        value 57;
        description
          "NE40E-X16A chassis.";
      }
      enum "fname8090NE40E-X16A-HVDC" {
        value 58;
        description
          "NE40E-X16A-HVDC chassis.";
      }
      enum "fname8090NE40E-X8A-HVDC" {
        value 59;
        description
          "NE40E-X8A-HVDC chassis.";
      }
      enum "fnameME60-X16A-HVDC" {
        value 60;
        description
          "ME60-X16A-HVDC chassis.";
      }
      enum "fnameME60-X8A-HVDC" {
        value 61;
        description
          "ME60-X8A-HVDC chassis.";
      }
      enum "fname8090CX600-X16A-HVDC" {
        value 62;
        description
          "CX600-X16A-HVDC chassis.";
      }
      enum "fname8090CX600-X8A-HVDC" {
        value 63;
        description
          "CX600-X8A-HVDC chassis.";
      }
      enum "fnamePTN6900-16A-HVDC" {
        value 64;
        description
          "PTN 6900-16A-HVDC chassis.";
      }
      enum "fnamePTN6900-8A-HVDC" {
        value 65;
        description
          "PTN 6900-8A-HVDC chassis.";
      }
      enum "fname8090CX600-X16A-DO-HVDC" {
        value 66;
        description
          "CX600-X16A-DO-HVDC chassis.";
      }
      enum "fname8090CX600-X8A-DO-HVDC" {
        value 67;
        description
          "CX600-X8A-DO-HVDC chassis.";
      }
      enum "fname8090NE40E-X16A-AC" {
        value 68;
        description
          "NE40E-X16A-AC chassis.";
      }
      enum "fname8090NE40E-X8A-AC" {
        value 69;
        description
          "NE40E-X8A-AC chassis.";
      }
      enum "fnameME60-X16A-AC" {
        value 70;
        description
          "ME60-X16A-AC chassis.";
      }
      enum "fnameME60-X8A-AC" {
        value 71;
        description
          "ME60-X8A-AC chassis.";
      }
      enum "fname8090CX600-X16A-AC" {
        value 72;
        description
          "CX600-X16A-AC chassis.";
      }
      enum "fname8090CX600-X8A-AC" {
        value 73;
        description
          "CX600-X8A-AC chassis.";
      }
      enum "fnamePTN6900-16A-AC" {
        value 74;
        description
          "PTN 6900-16A-AC chassis.";
      }
      enum "fnamePTN6900-8A-AC" {
        value 75;
        description
          "PTN 6900-8A-AC chassis.";
      }
      enum "fname8090CX600-X16A-DO-AC" {
        value 76;
        description
          "CX600-X16A-DO-AC chassis.";
      }
      enum "fname8090CX600-X8A-DO-AC" {
        value 77;
        description
          "CX600-X8A-DO-AC chassis.";
      }
      enum "fname8090NE40E-X16A-DC" {
        value 78;
        description
          "NE40E-X16A-DC chassis.";
      }
      enum "fname8090NE40E-X8A" {
        value 79;
        description
          "NE40E-X8A chassis.";
      }
      enum "fname8090NE40E-X8A-DC" {
        value 80;
        description
          "NE40E-X8A-DC chassis.";
      }
      enum "fname8090NE40E-X2-M8-AC" {
        value 81;
        description
          "NE40E-X2-M8-AC chassis.";
      }
      enum "fname8090NE40E-X2-M16" {
        value 82;
        description
          "NE40E-X2-M16 chassis.";
      }
      enum "fname8090NE20E-S4" {
        value 83;
        description
          "NE20E-S4 chassis.";
      }
      enum "fname8090NE20E-S8-AC" {
        value 84;
        description
          "NE20E-S8-AC chassis.";
      }
      enum "fname8090NE20E-S16" {
        value 85;
        description
          "NE20E-S16 chassis.";
      }
      enum "fname8090PTN6900-1-M4" {
        value 86;
        description
          "PTN 6900-1-M4 Chassis.";
      }
      enum "fname8090PTN6900-2-M8-AC" {
        value 87;
        description
          "PTN 6900-2-M8-AC Chassis.";
      }
      enum "fname8090PTN6900-2-M16" {
        value 88;
        description
          "PTN 6900-2-M16 Chassis.";
      }
      enum "fnamePTN6900-M2E" {
        value 89;
        description
          "PTN 6900-M2E chassis.";
      }
      enum "fnamePTN6900-M2F" {
        value 90;
        description
          "PTN 6900-M2F chassis.";
      }
      enum "fnamePTN6900-M2K" {
        value 91;
        description
          "PTN 6900-M2K chassis.";
      }      
      enum "fname8090NE40E-M2H" {
        value 92;
        description
          "NE40E-M2H chassis.";
      }
      enum "fname8031CX600-M2H" {
        value 93;
        description
          "CX600-M2H chassis.";
      }
      enum "fname8031CX600-M2K" {
        value 94;
        description
          "CX600-M2K chassis.";
      }
      enum "fname8090NE40E-M2K" {
        value 95;
        description
          "NE40E-M2K chassis.";
      }
      enum "fname8090CX6602" {
        value 96;
        description
          "CX6602 chassis.";
      }
      enum "fname8031CX600-M2K-DC" {
        value 97;
        description
          "CX600-M2K-DC chassis.";
      }
      enum "fname8031CX600-M2K-B-DC" {
        value 98;
        description
          "CX600-M2K-B-DC chassis.";
      }
      enum "fnamePTN6900-M2K-DC" {
        value 99;
        description
          "PTN6900-M2K-DC chassis.";
      }
      enum "fnamePTN6900-M2K-B-DC" {
        value 100;
        description
          "PTN6900-M2K-B-DC chassis.";
      }
      enum "fname8090CX6602-B-DC" {
        value 101;
        description
          "CX6602-B-DC chassis.";
      }
      enum "fname8090CX6602-DC" {
        value 102;
        description
          "CX6602-DC chassis.";
      }
      enum "fname8090NE40E-M2K-B-DC" {
        value 103;
        description
          "NE40E-M2K-B-DC chassis.";
      }
      enum "fname8090NE40E-M2K-DC" {
        value 104;
        description
          "NE40E-M2K-DC chassis.";
      }
      enum "fnamePTN6900-M2K-AC" {
        value 105;
        description
          "PTN6900-M2K-AC chassis.";
      }
      enum "fname8031CX600-M2K-AC" {
        value 106;
        description
          "CX600-M2K-AC chassis.";
      }
      enum "fname8031CX600-M2K-B-AC" {
        value 107;
        description
          "CX600-M2K-B-AC chassis.";
      }
      enum "fname8090CX6602-AC" {
        value 108;
        description
          "CX6602-AC chassis.";
      }
      enum "fnamePTN6900-M2K-B-AC" {
        value 109;
        description
          "M2K-B-AC chassis.";
      }
      enum "fname8090NE40E-M2K-B-AC" {
        value 110;
        description
          "NE40E-M2K-B-AC chassis.";
      }
      enum "fname8090NE40E-M2K-AC" {
        value 111;
        description
          "NE40E-M2K-AC chassis.";
      }
      enum "fname8090CX6602-B-AC" {
        value 112;
        description
          "CX6602-B-AC chassis.";
      }
      enum "fname8031CX600-M2E-AC" {
        value 113;
        description
          "CX600-M2E-AC chassis.";
      }
      enum "fname8090NE40E-M2E-AC" {
        value 114;
        description
          "NE40E-M2E-AC chassis.";
      }
      enum "fnameNE20E-S2E-AC" {
        value 115;
        description
          "NE20E-S2E-AC chassis.";
      }
      enum "fnamePTN6900-M2E-AC" {
        value 116;
        description
          "PTN6900-M2E-AC chassis.";
      }
      enum "fname8031CX600-M2E-DC" {
        value 117;
        description
          "CX600-M2E-DC chassis.";
      }
      enum "fname8090NE40E-M2E-DC" {
        value 118;
        description
          "NE40E-M2E-DC chassis.";
      }
      enum "fnameNE20E-S2E-DC" {
        value 119;
        description
          "NE20E-S2E-DC chassis.";
      }
      enum "fnamePTN6900-M2E-DC" {
        value 120;
        description
          "PTN6900-M2E-DC chassis.";
      }
      enum "fname8031CX600-M2F-AC" {
        value 121;
        description
          "CX600-M2F-AC chassis.";
      }
      enum "fname8090NE40E-M2F-AC" {
        value 122;
        description
          "NE40E-M2F-AC chassis.";
      }
      enum "fnameNE20E-S2F-AC" {
        value 123;
        description
          "NE20E-S2F-AC chassis.";
      }
      enum "fnamePTN6900-M2F-AC" {
        value 124;
        description
          "PTN6900-M2F-AC chassis.";
      }
      enum "fname8031CX600-M2F-DC" {
        value 125;
        description
          "CX600-M2F-DC chassis.";
      }
      enum "fname8090NE40E-M2F-DC" {
        value 126;
        description
          "NE40E-M2F-DC chassis.";
      }
      enum "fnameNE20E-S2F-DC" {
        value 127;
        description
          "NE20E-S2F-DC chassis.";
      }
      enum "fnamePTN6900-M2F-DC" {
        value 128;
        description
          "PTN6900-M2F-DC chassis.";
      }
      enum "fname8031CX600-M2H-AC" {
        value 129;
        description
          "CX600-M2H-AC chassis.";
      }
      enum "fname8090NE40E-M2H-AC" {
        value 130;
        description
          "NE40E-M2H-AC chassis.";
      }
      enum "fname8031CX600-M2H-DC" {
        value 131;
        description
          "CX600-M2H-DC chassis.";
      }
      enum "fname8090NE40E-M2H-DC" {
        value 132;
        description
          "NE40E-M2H-DC chassis.";
      }
      enum "fname8031CX600-M2K-B" {
        value 133;
        description
          "CX600-M2K-B chassis.";
      }
      enum "fname8090NE40E-M2K-B" {
        value 134;
        description
          "NE40E-M2K-B chassis.";
      }
      enum "fname8090CX6602-B" {
        value 135;
        description
          "CX6602-B chassis.";
      }
      enum "fnamePTN6900-M2K-B" {
        value 136;
        description
          "PTN 6900-M2K-B chassis.";
      }
      enum "fname8031CX600-F1A-14H24Q" {
        value 137;
        description
          "CX600-F1A-14H24Q chassis.";
      }
      enum "fname8090NE40E-F1A-14H24Q" {
        value 138;
        description
          "NE40E-F1A-14H24Q chassis.";
      }
      enum "fname8090CX6601-14H24Q" {
        value 139;
        description
          "CX6601-14H24Q chassis.";
      }
      enum "fnamePTN6900-F1A-14H24Q" {
        value 140;
        description
          "PTN6900-F1A-14H24Q chassis.";
      }
      enum "fname8090CX600-X8" {
        value 141;
        description
          "CX600-X8 chassis.";
      }
      enum "fname8090CX600-X8A" {
        value 142;
        description
          "CX600-X8A chassis.";
      }
      enum "fname8090CX600-X8A-DC" {
        value 143;
        description
          "CX600-X8A-DC chassis.";
      }
      enum "fname8090CX600-X16" {
        value 144;
        description
          "CX600-X16 chassis.";
      }
      enum "fname8090CX600-X16A" {
        value 145;
        description
          "CX600-X16A chassis.";
      }
      enum "fname8090CX600-X16A-DC" {
        value 146;
        description
          "CX600-X16A-DC chassis.";
      }
      enum "fname8090NE5000E-X8" {
        value 147;
        description
          "NE5000EX8 Chassis.";
      }
      enum "fname8090NE5000E-20" {
        value 148;
        description
          "NE5000E-20 Chassis.";
      }
      enum "fname8090NE9000-20" {
        value 149;
        description
          "NE9000-20 Chassis.";
      }
      enum "fname8090NE9000-8" {
        value 150;
        description
          "NE9000-8 Chassis.";
      }
      enum "fnamePTN6900TNRK003BKP01" {
        value 151;
        description
          "PTN 6900-3 chassis.";
      }
      enum "fnamePTN6900TNRZ1BKPE" {
        value 152;
        description
          "PTN 6900-3-DC chassis.";
      }
      enum "fname8031CX6003AC" {
        value 153;
        description
          "CX600-X3 chassis.";
      }
      enum "fname8031CX6003DCDO" {
        value 154;
        description
          "CX600-X3-DC-DO chassis.";
      }
      enum "fname8031CX6003ACDO" {
        value 155;
        description
          "CX600-X3-AC-DO chassis.";
      }
      enum "fname8031CX600X8DO" {
        value 156;
        description
          "CX600-X8-DO chassis.";
      }
      enum "fname8031CX6003DC" {
        value 157;
        description
          "CX600-X3-DC chassis.";
      }
      enum "fname8090NE40E3AC" {
        value 158;
        description
          "NE40E-X3 chassis.";
      }
      enum "fname8090NE40E3DC" {
        value 159;
        description
          "NE40E-X3-DC chassis.";
      }
      enum "fnameME60-X3-AC" {
        value 160;
        description
          "ME60-X3 chassis.";
      }
      enum "fnameME60-X3-DC" {
        value 161;
        description
          "ME60-X3-DC chassis.";
      }
      enum "fnamePTN6900-3A" {
        value 162;
        description
          "PTN 6900-3A chassis.";
      }
      enum "fnameME60-X3A" {
        value 163;
        description
          "ME60-X3A chassis.";
      }
      enum "fname8090NE40E-X3A" {
        value 164;
        description
          "NE40E-X3A chassis.";
      }
      enum "fname8031CX600-X3A" {
        value 165;
        description
          "CX600-X3A chassis.";
      }
      enum "fnameME60-X8" {
        value 166;
        description
          "ME60-X8 chassis.";
      }
      enum "fnameME60-X16" {
        value 167;
        description
          "ME60-X16 chassis.";
      }
      enum "fnameME60-X8A" {
        value 168;
        description
          "ME60-X8A chassis.";
      }
      enum "fnameME60-X8A-DC" {
        value 169;
        description
          "ME60-X8A-DC chassis.";
      }
      enum "fnameME60-X16A" {
        value 170;
        description
          "ME60-X16A chassis.";
      }
      enum "fnameME60-X16A-DC" {
        value 171;
        description
          "ME60-X16A-DC chassis.";
      }
      enum "fnamePTN6900Half" {
        value 172;
        description
          "PTN 6900-8 chassis.";
      }
      enum "fnamePTN6900Whole" {
        value 173;
        description
          "PTN 6900-16 chassis.";
      }
      enum "fnamePTN6900-8A" {
        value 174;
        description
          "PTN 6900-8A chassis.";
      }
      enum "fnamePTN6900-8A-DC" {
        value 175;
        description
          "PTN 6900-8A-DC chassis.";
      }
      enum "fnamePTN6900-16A" {
        value 176;
        description
          "PTN 6900-16A chassis.";
      }
      enum "fnamePTN6900-16A-DC" {
        value 177;
        description
          "PTN 6900-16A-DC chassis.";
      }
      enum "fname8090CX600-X8A-DO" {
        value 178;
        description
          "CX600-X8A-DO chassis.";
      }
      enum "fname8090CX600-X8A-DO-DC" {
        value 179;
        description
          "CX600-X8A-DO-DC chassis.";
      }
      enum "fname8090CX600-X16A-DO" {
        value 180;
        description
          "CX600-X16A-DO chassis.";
      }
      enum "fname8090CX600-X16A-DO-DC" {
        value 181;
        description
          "CX600-X16A-DO-DC chassis.";
      }
      enum "fname8090CX600-X16-DO" {
        value 182;
        description
          "CX600-X16-DO chassis.";
      }
      enum "fname8031CX600-X3A-DO" {
        value 183;
        description
          "CX600-X3A-DO chassis.";
      }
      enum "fname8090CX600-X2-M8A-AC" {
        value 184;
        description
          "CX600-X2-M8A-AC chassis.";
      }
      enum "fname8090CX600-X2-M8A-DC" {
        value 185;
        description
          "CX600-X2-M8A-DC chassis.";
      }
      enum "fname8031CX600-M8ADO" {
        value 186;
        description
          "CX600-M8ADO chassis.";
      }
      enum "fname8031CX600-M8ADO-DC" {
        value 187;
        description
          "CX600-M8ADO-DC chassis.";
      }
      enum "fname8090NE20E-S8A-AC" {
        value 188;
        description
          "NE20E-S8A-AC chassis.";
      }
      enum "fname8090NE20E-S8A-DC" {
        value 189;
        description
          "NE20E-S8A-DC chassis.";
      }
      enum "fname8090NE40E-X2-M8A-AC" {
        value 190;
        description
          "NE40E-X2-M8A-AC chassis.";
      }
      enum "fname8090NE40E-X2-M8A-DC" {
        value 191;
        description
          "NE40E-X2-M8A-DC chassis.";
      }
      enum "fname8090PTN6900-2-M8A-AC" {
        value 192;
        description
          "PTN 6900-2-M8A-AC chassis.";
      }
      enum "fname8090PTN6900-2-M8A-DC" {
        value 193;
        description
          "PTN 6900-2-M8A-DC chassis.";
      }
      enum "fnameME60-X2-M8A-AC" {
        value 194;
        description
          "ME60-X2-M8A-AC chassis.";
      }
      enum "fnameME60-X2-M8A-DC" {
        value 195;
        description
          "ME60-X2-M8A-DC chassis.";
      }
      enum "fname8090CX600-X2-M16A" {
        value 196;
        description
          "CX600-X2-M16A chassis.";
      }
      enum "fname8031CX600-M16ADO" {
        value 197;
        description
          "CX600-M16ADO chassis.";
      }
      enum "fname8090CX600-X2-M16B" {
        value 198;
        description
          "CX600-X2-M16B chassis.";
      }
      enum "fname8090NE20E-S16A" {
        value 199;
        description
          "NE20E-S16A chassis.";
      }
      enum "fname8090NE20E-S16B" {
        value 200;
        description
          "NE20E-S16B chassis.";
      }
      enum "fname8090NE40E-X2-M16A" {
        value 201;
        description
          "NE40E-X2-M16A chassis.";
      }
      enum "fname8090NE40E-X2-M16B" {
        value 202;
        description
          "NE40E-X2-M16B chassis.";
      }
      enum "fname8090PTN6900-2-M16A" {
        value 203;
        description
          "PTN 6900-2-M16A chassis.";
      }
      enum "fname8090PTN6900-2-M16B" {
        value 204;
        description
          "PTN 6900-2-M16B chassis.";
      }
      enum "fnameME60-X2-M16A" {
        value 205;
        description
          "ME60-X2-M16A chassis.";
      }
      enum "fname8090CX600-M8-DC" {
        value 206;
        description
          "CX600-M8-DC chassis.";
      }
      enum "fname8090CX600-X2-M8-DC" {
        value 207;
        description
          "CX600-X2-M8-DC chassis.";
      }
      enum "fname8090CX600-M8A-DC" {
        value 208;
        description
          "CX600-X2-M8A-DC chassis.";
      }
      enum "fname8090CX600-M8A-AC" {
        value 209;
        description
          "CX600-X2-M8A-AC chassis.";
      }
      enum "fname8090NE40E-X2-M8-DC" {
        value 210;
        description
          "NE40E-X2-M8-DC chassis.";
      }
      enum "fname8090NE20E-S8-DC" {
        value 211;
        description
          "NE20E-S8-DC chassis.";
      }
      enum "fname8090PTN6900-2-M8-DC" {
        value 212;
        description
          "PTN 6900-2-M8-DC Chassis.";
      }
      enum "fnameME60-X2-M8-AC" {
        value 213;
        description
          "ME60-X2-M8-AC chassis.";
      }
      enum "fnameME60-X2-M8-DC" {
        value 214;
        description
          "ME60-X2-M8-DC chassis.";
      }
      enum "fnameME60-X2-M16" {
        value 215;
        description
          "ME60-X2-M16 chassis.";
      }
      enum "fname8090CX6620" {
        value 216;
        description
          "CX6620 Chassis.";
      }
      enum "fname8090CX6608" {
        value 217;
        description
          "CX6608 Chassis.";
      }
      enum "fname8090NE9000-20-LS" {
        value 218;
        description
          "NE9000-20-LS Chassis.";
      }
      enum "fname8090NE9000-8-LS" {
        value 219;
        description
          "NE9000-8-LS Chassis.";
      }
      enum "fnameNETENGINE-8000-F1A-8H20Q" {
        value 220;
        description
          "NETENGINE-8000-F1A-8H20Q chassis.";
      }
      enum "fnameNETENGINE-8000-F1A-8H20Q-AC" {
        value 221;
        description
          "NETENGINE-8000-F1A-8H20Q-AC chassis.";
      }
      enum "fnameNETENGINE-8000-F1A-8H20Q-DC" {
        value 222;
        description
          "NETENGINE-8000-F1A-8H20Q-DC chassis.";
      }
      enum "ATN910C-G" {
        value 223;
        description
          "ATN910C-G chassis.";
      }
      enum "fnameNETENGINE-8000-M14-AC" {
        value 224;
        description
          "NETENGINE-8000-M14-AC chassis.";
      }
      enum "fnameNETENGINE-8000-M14-DC" {
        value 225;
        description
          "NETENGINE-8000-M14-DC chassis.";
      }
      enum "fnameNE40E-X2-M14-AC" {
        value 226;
        description
          "NE40E-X2-M14-AC chassis.";
      }
      enum "fnameNE40E-X2-M14-DC" {
        value 227;
        description
          "NE40E-X2-M14-DC chassis.";
      }
      enum "fnamePTN6900-2-M14-AC" {
        value 228;
        description
          "PTN6900-2-M14-AC chassis.";
      }
      enum "fnamePTN6900-2-M14-DC" {
        value 229;
        description
          "PTN6900-2-M14-DC chassis.";
      }
      enum "fnameNETENGINE-8000-M8" {
        value 230;
        description
          "NETENGINE-8000-M8 chassis.";
      }
      enum "fnameNETENGINE-8000-M8-AC" {
        value 231;
        description
          "NETENGINE-8000-M8-AC chassis.";
      }
      enum "fnameNETENGINE-8000-M8-DC" {
        value 232;
        description
          "NETENGINE-8000-M8-DC chassis.";
      }
      enum "fnamePTN6900-2-M8C" {
        value 233;
        description
          "PTN6900-2-M8C chassis.";
      }
      enum "fnamePTN6900-2-M8C-AC" {
        value 234;
        description
          "PTN6900-2-M8C-AC chassis.";
      }
      enum "fnamePTN6900-2-M8C-DC" {
        value 235;
        description
          "PTN6900-2-M8C-DC chassis.";
      }
      enum "fnameNETENGINE-8000-X4-HVDC" {
        value 236;
        description
          "NETENGINE-8000-X4-HVDC chassis.";
      }
      enum "fnameNETENGINE-8000-X4-DC" {
        value 237;
        description
          "NETENGINE-8000-X4-DC chassis.";
      }
      enum "fnameNETENGINE-8000-X8-HVDC" {
        value 238;
        description
          "NETENGINE-8000-X8-HVDC chassis.";
      }
      enum "fnameNETENGINE-8000-X8-DC" {
        value 239;
        description
          "NETENGINE-8000-X8-DC chassis.";
      }
      enum "ATN950D-AC" {
        value 240;
        description
          "ATN950D-AC chassis.";
      }
      enum "ATN950D-DC" {
        value 241;
        description
          "ATN950D-DC chassis.";
      }
      enum "fnameNETENGINE-8000-M6-AC" {
        value 242;
        description
          "NETENGINE-8000-M6-AC chassis.";
      }
      enum "fnameNETENGINE-8000-M6-DC" {
        value 243;
        description
          "NETENGINE-8000-M6-DC chassis.";
      }
    }
    description
      "Hardware-chassis-type.";
  }
  
  typedef hardware-board-type {
    type enumeration {
      enum "unknown" {
        value 0;
        description
          "Unknown device.";
      }
      enum "ANPM001AICF0" {
        value 1;
        description
          "ANPM001AICF0.";
      }
      enum "CR5B0BKP0383" {
        value 2;
        description
          "CR5B0BKP0383.";
      }
      enum "CR5B0BKP0382" {
        value 3;
        description
          "CR5B0BKP0382.";
      }
      enum "ANPM001DICF0" {
        value 4;
        description
          "ANPM001DICF0.";
      }
      enum "LNPM001AICF0" {
        value 5;
        description
          "LNPM001AICF0.";
      }
      enum "ANDD03CXPA00" {
        value 6;
        description
          "ANDD03CXPA00.";
      }
      enum "ANGMHSTE0110" {
        value 7;
        description
          "ANGMHSTE0110.";
      }
      enum "ANKD00CXPB02" {
        value 8;
        description
          "ANKD00CXPB02.";
      }
      enum "NEDD00CXPB00" {
        value 9;
        description
          "NEDD00CXPB00.";
      }
      enum "NECM000AIC01" {
        value 10;
        description
          "NECM000AIC01.";
      }
      enum "NEJD00CXPA00" {
        value 11;
        description
          "NEJD00CXPA00.";
      }
      enum "ANKD00CXPA00" {
        value 12;
        description
          "ANKD00CXPA00.";
      }
      enum "ANK200CXPA00" {
        value 13;
        description
          "ANK200CXPA00.";
      }
      enum "ANKD00CXPB00" {
        value 14;
        description
          "ANKD00CXPB00.";
      }
      enum "ANGMHSTA0111" {
        value 15;
        description
          "ANGMHSTA0111.";
      }
      enum "ANGMHSTA0211" {
        value 16;
        description
          "ANGMHSTA0211.";
      }
      enum "ANGMHSTB0111" {
        value 17;
        description
          "ANGMHSTB0111.";
      }
      enum "ANGMHSTB0211" {
        value 18;
        description
          "ANGMHSTB0211.";
      }
      enum "ANGMHSTD0100" {
        value 19;
        description
          "ANGMHSTD0100.";
      }
      enum "ANGMHSTD0200" {
        value 20;
        description
          "ANGMHSTD0200.";
      }
      enum "ANGMHSTF0110" {
        value 21;
        description
          "ANGMHSTF0110.";
      }
      enum "ANGMHSTA0311" {
        value 22;
        description
          "ANGMHSTA0311.";
      }
      enum "ANGMHSTB0311" {
        value 23;
        description
          "ANGMHSTB0311.";
      }
      enum "ANGMHSTD0311" {
        value 24;
        description
          "ANGMHSTD0311.";
      }
      enum "NECMHSTA0211" {
        value 25;
        description
          "NECMHSTA0211.";
      }
      enum "NECMHSTB0211" {
        value 26;
        description
          "NECMHSTB0211.";
      }
      enum "NEDD00CXPA00" {
        value 27;
        description
          "NEDD00CXPA00.";
      }
      enum "ANJ1CXP" {
        value 28;
        description
          "ANJD00CXPA01.";
      }
      enum "TNF5PIU" {
        value 29;
        description
          "ANJ0000PIU00.";
      }
      enum "TPJ1PIU" {
        value 30;
        description
          "ANJ0000PIU00.";
      }
      enum "TNF5APIU" {
        value 31;
        description
          "ANJ000APIU00.";
      }
      enum "ANKD000PIU00" {
        value 32;
        description
          "ANKD000PIU00.";
      }
      enum "ANGD00APIU00" {
        value 33;
        description
          "ANGD00APIU00.";
      }
      enum "ES5M0PSD1700" {
        value 34;
        description
          "ES5M0PSD1700.";
      }
      enum "ANKD000FAN00" {
        value 35;
        description
          "ANKD000FAN00.";
      }
      enum "NEDD000FAN00" {
        value 36;
        description
          "NEDD000FAN00.";
      }
      enum "TNCM000PIU00" {
        value 37;
        description
          "TNCM000PIU00.";
      }
      enum "NECD001FAN00" {
        value 38;
        description
          "NECD001FAN00.";
      }
      enum "NEJD002FAN00" {
        value 39;
        description
          "NEJD002FAN00.";
      }
      enum "ANGD000FAN00" {
        value 40;
        description
          "ANGD000FAN00.";
      }
      enum "ANJ1FAN" {
        value 41;
        description
          "ANJE000FAN00.";
      }
      enum "ANJD00CXPA01" {
        value 42;
        description
          "ANJD00CXPA01.";
      }
      enum "ANJ0002CXP00" {
        value 43;
        description
          "ANJ0002CXP00.";
      }
      enum "ANJE000FAN00" {
        value 44;
        description
          "ANJE000FAN00.";
      }
      enum "ANJ0000PIU00" {
        value 45;
        description
          "ANJ0000PIU00.";
      }
      enum "ANJ000APIU00" {
        value 46;
        description
          "ANJ000APIU00.";
      }
      enum "ADDD00CXPA02" {
        value 47;
        description
          "ADDD00CXPA02.";
      }
      enum "ANDD00CXPB02" {
        value 48;
        description
          "ANDD00CXPB02.";
      }
      enum "ANDD00CXPE02" {
        value 49;
        description
          "ANDD00CXPE02.";
      }
      enum "ANGM000HSA00" {
        value 50;
        description
          "ANGM000HSA00.";
      }
      enum "ANGM000HSB00" {
        value 51;
        description
          "ANGM000HSB00.";
      }
      enum "ANGM0HSDNA02" {
        value 52;
        description
          "ANGM0HSDNA02.";
      }
      enum "ANGM0HSDND00" {
        value 53;
        description
          "ANGM0HSDND00.";
      }
      enum "ANGM0HSDNA01" {
        value 54;
        description
          "ANGM0HSDNA01.";
      }
      enum "ANGM01HSDD00" {
        value 55;
        description
          "ANGM01HSDD00.";
      }
      enum "ANGM02HSDA00" {
        value 56;
        description
          "ANGM02HSDA00.";
      }
      enum "ANGM01HSDD01" {
        value 57;
        description
          "ANGM01HSDD01.";
      }
      enum "ANGM02HSDA01" {
        value 58;
        description
          "ANGM02HSDA01.";
      }
      enum "ANCD000FAN00" {
        value 59;
        description
          "ANCD000FAN00.";
      }
      enum "ANCD000PIU00" {
        value 60;
        description
          "ANCD000PIU00.";
      }
      enum "ANCD00APIU00" {
        value 61;
        description
          "ANCD00APIU00.";
      }
      enum "ANDD000FAN02" {
        value 62;
        description
          "ANDD000FAN02.";
      }
      enum "ANDD002PIU00" {
        value 63;
        description
          "ANDD002PIU00.";
      }
      enum "CX6D00MPUD11" {
        value 64;
        description
          "CX6D00MPUD11.";
      }
      enum "CX6D00MPUD30" {
        value 65;
        description
          "CX6D00MPUD30.";
      }
      enum "CX6D0SRUA611" {
        value 66;
        description
          "CX6D0SRUA611.";
      }
      enum "CX6DSFUIA07C" {
        value 67;
        description
          "CX6DSFUIA07C.";
      }
      enum "CX6DL2XEIG1B" {
        value 68;
        description
          "CX6DL2XEIG1B.";
      }
      enum "CX6DL4XEBG1B" {
        value 69;
        description
          "CX6DL4XEBG1B.";
      }
      enum "CX6D0L5XFA11" {
        value 70;
        description
          "CX6D0L5XFA11.";
      }
      enum "CR5D0EFGFA73" {
        value 71;
        description
          "CR5D0EFGFA73.";
      }
      enum "CR5DL1XEDG70" {
        value 72;
        description
          "CR5DL1XEDG70.";
      }
      enum "CX6D0LAXFA11" {
        value 73;
        description
          "CX6D0LAXFA11.";
      }
      enum "CX6DISUF5010" {
        value 74;
        description
          "CX6DISUF5010.";
      }
      enum "CR5DLPUF5071" {
        value 75;
        description
          "CR5DLPUF5071.";
      }
      enum "CR5DLPUF507M" {
        value 76;
        description
          "CR5DLPUF507M.";
      }
      enum "CX6DISUF5011" {
        value 77;
        description
          "CX6DISUF5011.";
      }
      enum "CX6DL1XEDG1A" {
        value 78;
        description
          "CX6DL1XEDG1A.";
      }
      enum "CX6D0EFGFA12" {
        value 79;
        description
          "CX6D0EFGFA12.";
      }
      enum "CX6D0EMGFA10" {
        value 80;
        description
          "CX6D0EMGFA10.";
      }
      enum "ME0DMSUFF070" {
        value 81;
        description
          "ME0DMSUFF070.";
      }
      enum "CR5D00E2NC76" {
        value 82;
        description
          "CR5D00E2NC76.";
      }
      enum "CR5D00LEXF76" {
        value 83;
        description
          "CR5D00LEXF76.";
      }
      enum "CR5DE1NLAX76" {
        value 84;
        description
          "CR5DE1NLAX76.";
      }
      enum "CR5D00E2NC75" {
        value 85;
        description
          "CR5D00E2NC75.";
      }
      enum "CR5D00LEXF75" {
        value 86;
        description
          "CR5D00LEXF75.";
      }
      enum "CR5DLPUFE07B" {
        value 87;
        description
          "CR5DLPUFE07B.";
      }
      enum "CR5DLPUFE071" {
        value 88;
        description
          "CR5DLPUFE071.";
      }
      enum "CR5DLPUFE07C" {
        value 89;
        description
          "CR5DLPUFE07C.";
      }
      enum "CR5DE1NLAX75" {
        value 90;
        description
          "CR5DE1NLAX75.";
      }
      enum "CR5D0E6MFA70" {
        value 91;
        description
          "CR5D0E6MFA70.";
      }
      enum "CR5D0E6MFA71" {
        value 92;
        description
          "CR5D0E6MFA71.";
      }
      enum "CR52MPUA" {
        value 93;
        description
          "CR52MPUA.";
      }
      enum "CR52MPUB" {
        value 94;
        description
          "CR52MPUB.";
      }
      enum "CR55MPUA" {
        value 95;
        description
          "CR55MPUA.";
      }
      enum "CR55MPUAB" {
        value 96;
        description
          "CR55MPUAB.";
      }
      enum "CR56RPUA" {
        value 97;
        description
          "CR56RPUA.";
      }
      enum "CR52LPUA" {
        value 98;
        description
          "CR52LPUA.";
      }
      enum "CR52LPUB" {
        value 99;
        description
          "CR52LPUB.";
      }
      enum "CR52LPUC" {
        value 100;
        description
          "CR52LPUC.";
      }
      enum "CR52LPUE" {
        value 101;
        description
          "CR52LPUE.";
      }
      enum "CR52LPUR" {
        value 102;
        description
          "CR52LPUR.";
      }
      enum "CR52LPUF" {
        value 103;
        description
          "CR52LPUF.";
      }
      enum "CR52LPUG" {
        value 104;
        description
          "CR52LPUG.";
      }
      enum "CR52LPUH" {
        value 105;
        description
          "CR52LPUH.";
      }
      enum "CR52LPUI" {
        value 106;
        description
          "CR52LPUI.";
      }
      enum "CR52LPUK" {
        value 107;
        description
          "CR52LPUK.";
      }
      enum "CR52LPUM" {
        value 108;
        description
          "CR52LPUM.";
      }
      enum "CR52LPUN" {
        value 109;
        description
          "CR52LPUN.";
      }
      enum "CR52SPUC" {
        value 110;
        description
          "CR52SPUC.";
      }
      enum "CR56LPUF100A" {
        value 111;
        description
          "CR56LPUF100A.";
      }
      enum "CR56LPUF100B" {
        value 112;
        description
          "CR56LPUF100B.";
      }
      enum "CR56LPUI100A" {
        value 113;
        description
          "CR56LPUI100A.";
      }
      enum "CR56LPUI100B" {
        value 114;
        description
          "CR56LPUI100B.";
      }
      enum "CR56LPUI100C" {
        value 115;
        description
          "CR56LPUI100C.";
      }
      enum "CR56LPUF200A" {
        value 116;
        description
          "CR56LPUF200A.";
      }
      enum "CR52SFUA" {
        value 117;
        description
          "CR52SFUA.";
      }
      enum "CR52SRUA" {
        value 118;
        description
          "CR52SRUA.";
      }
      enum "CR52SFUD" {
        value 119;
        description
          "CR52SFUD.";
      }
      enum "CR52SFUF" {
        value 120;
        description
          "CR52SFUF.";
      }
      enum "CR52SFUG" {
        value 121;
        description
          "CR52SFUG.";
      }
      enum "CR52SFUC" {
        value 122;
        description
          "CR52SFUC.";
      }
      enum "CR52SFEA" {
        value 123;
        description
          "CR52SFEA.";
      }
      enum "CR52K-SFEA" {
        value 124;
        description
          "CR52K-SFEA.";
      }
      enum "CR55SFUA" {
        value 125;
        description
          "CR55SFUA.";
      }
      enum "CR55ECUA" {
        value 126;
        description
          "CR55ECUA.";
      }
      enum "CR55C-ECUA" {
        value 127;
        description
          "CR55C-ECUA.";
      }
      enum "CR55ICUA" {
        value 128;
        description
          "CR55ICUA.";
      }
      enum "CR56SFUF100B" {
        value 129;
        description
          "CR56SFUF100B.";
      }
      enum "CR55SFUI100A" {
        value 130;
        description
          "CR55SFUI100A.";
      }
      enum "CR55ECU100A" {
        value 131;
        description
          "CR55ECU100A.";
      }
      enum "CR52SFEB" {
        value 132;
        description
          "CR52SFEB.";
      }
      enum "CR56SFUF100C" {
        value 133;
        description
          "CR56SFUF100C.";
      }
      enum "CR56SFU200A" {
        value 134;
        description
          "CR56SFU200A.";
      }
      enum "CR5D00EKGF60" {
        value 135;
        description
          "CR5D00EKGF60.";
      }
      enum "CR5D00P8UF61" {
        value 136;
        description
          "CR5D00P8UF61.";
      }
      enum "CR5D00E4XX60" {
        value 137;
        description
          "CR5D00E4XX60.";
      }
      enum "CR5D00W4XX60" {
        value 138;
        description
          "CR5D00W4XX60.";
      }
      enum "CR5DLPUFA060" {
        value 139;
        description
          "CR5DLPUFA060.";
      }
      enum "CR5D00LEXF60" {
        value 140;
        description
          "CR5D00LEXF60.";
      }
      enum "CR5D00E2NC60" {
        value 141;
        description
          "CR5D00E2NC60.";
      }
      enum "CR5DE1NLAX60" {
        value 142;
        description
          "CR5DE1NLAX60.";
      }
      enum "CR5D00E1NC60" {
        value 143;
        description
          "CR5D00E1NC60.";
      }
      enum "CR5D00LAXX60" {
        value 144;
        description
          "CR5D00LAXX60.";
      }
      enum "CR5DSFEBA06B" {
        value 145;
        description
          "CR5DSFEBA06B.";
      }
      enum "CR5D0MPUB461" {
        value 146;
        description
          "CR5D0MPUB461.";
      }
      enum "CR5DSFUFA06B" {
        value 147;
        description
          "CR5DSFUFA06B.";
      }
      enum "CR5DSFUIE060" {
        value 148;
        description
          "CR5DSFUIE060.";
      }
      enum "CR5DSFUFA06C" {
        value 149;
        description
          "CR5DSFUFA06C.";
      }
      enum "CR5D0MPUA450" {
        value 150;
        description
          "CR5D0MPUA450.";
      }
      enum "CR5DECUFA050" {
        value 151;
        description
          "CR5DECUFA050.";
      }
      enum "CR5DSFUIA050" {
        value 152;
        description
          "CR5DSFUIA050.";
      }
      enum "CX6D00MPUK70" {
        value 153;
        description
          "CX6D00MPUK70.";
      }
      enum "CX6PM2EBAS70" {
        value 154;
        description
          "CX6PM2EBAS70.";
      }
      enum "CX6PM2EBAS71" {
        value 155;
        description
          "CX6PM2EBAS71.";
      }
      enum "CX6PM2FBAS70" {
        value 156;
        description
          "CX6PM2FBAS70.";
      }
      enum "CX6PM2FBAS71" {
        value 157;
        description
          "CX6PM2FBAS71.";
      }
      enum "CR2P2EBASD10" {
        value 158;
        description
          "CR2P2EBASD10.";
      }
      enum "CR2P2EBASA10" {
        value 159;
        description
          "CR2P2EBASA10.";
      }
      enum "CR2P2FBASD10" {
        value 160;
        description
          "CR2P2FBASD10.";
      }
      enum "CR2P2FBASA10" {
        value 161;
        description
          "CR2P2FBASA10.";
      }
      enum "CR5PM2EBAS70" {
        value 162;
        description
          "CR5PM2EBAS70.";
      }
      enum "CR5PM2EBAS71" {
        value 163;
        description
          "CR5PM2EBAS71.";
      }
      enum "CR5PM2FBAS70" {
        value 164;
        description
          "CR5PM2FBAS70.";
      }
      enum "CR5PM2FBAS71" {
        value 165;
        description
          "CR5PM2FBAS71.";
      }
      enum "TNRPM2EBAS70" {
        value 166;
        description
          "TNRPM2EBAS70.";
      }
      enum "TNRPM2EBAS71" {
        value 167;
        description
          "TNRPM2EBAS71.";
      }
      enum "TNRPM2FBAS70" {
        value 168;
        description
          "TNRPM2FBAS70.";
      }
      enum "TNRPM2FBAS71" {
        value 169;
        description
          "TNRPM2FBAS71.";
      }
      enum "CR5PM2HBAS72" {
        value 170;
        description
          "CR5PM2HBAS72.";
      }
      enum "CX6PM2KBAS90" {
        value 171;
        description
          "CX6PM2KBAS90.";
      }
      enum "CX6PM2KBAS91" {
        value 172;
        description
          "CX6PM2KBAS91.";
      }
      enum "CX6B0BKP0391" {
        value 173;
        description
          "CX6B0BKP0391.";
      }
      enum "CR5PM2KBAS90" {
        value 174;
        description
          "CR5PM2KBAS90.";
      }
      enum "CR5PM2KBAS91" {
        value 175;
        description
          "CR5PM2KBAS91.";
      }
      enum "CR5B0BKP0391" {
        value 176;
        description
          "CR5B0BKP0391.";
      }
      enum "TNRB0BKP0373" {
        value 177;
        description
          "TNRB0BKP0373.";
      }
      enum "CX6P02ABAS00" {
        value 178;
        description
          "CX6P02ABAS00.";
      }
      enum "CX6P02ABAS01" {
        value 179;
        description
          "CX6P02ABAS01.";
      }
      enum "CX6P020BKP00" {
        value 180;
        description
          "CX6P020BKP00.";
      }
      enum "CX6B0BKP0393" {
        value 181;
        description
          "CX6B0BKP0393.";
      }
      enum "CR5B0BKP0393" {
        value 182;
        description
          "CR5B0BKP0393.";
      }
      enum "CX6P020BKP01" {
        value 183;
        description
          "CX6P020BKP01.";
      }
      enum "TNRB0BKP0374" {
        value 184;
        description
          "TNRB0BKP0374.";
      }
      enum "CR5PM2HBAS73" {
        value 185;
        description
          "CR5PM2HBAS73.";
      }
      enum "CR5B0BKP0377" {
        value 186;
        description
          "CR5B0BKP0377.";
      }
      enum "CX6PM2HBAS72" {
        value 187;
        description
          "CX6PM2HBAS72.";
      }
      enum "CX6PM2HBAS73" {
        value 188;
        description
          "CX6PM2HBAS73.";
      }
      enum "CX6B0BKP0375" {
        value 189;
        description
          "CX6B0BKP0375.";
      }
      enum "CR5B0BKP0392" {
        value 190;
        description
          "CR5B0BKP0392.";
      }
      enum "CX6B0BKP0392" {
        value 191;
        description
          "CX6B0BKP0392.";
      }
      enum "TNRB0BKP0391" {
        value 192;
        description
          "TNRB0BKP0391.";
      }
      enum "CX6P010BKP90" {
        value 193;
        description
          "CX6P010BKP90.";
      }
      enum "CX6B0BKP0394" {
        value 194;
        description
          "CX6B0BKP0394.";
      }
      enum "CR5B0BKP0394" {
        value 195;
        description
          "CR5B0BKP0394.";
      }
      enum "TNRB0BKP0394" {
        value 196;
        description
          "TNRB0BKP0394.";
      }
      enum "CX6D00MPUK10" {
        value 197;
        description
          "CX6D00MPUK10.";
      }
      enum "CR5D00MPUK70" {
        value 198;
        description
          "CR5D00MPUK70.";
      }
      enum "CR2D00MPUE10" {
        value 199;
        description
          "CR2D00MPUE10.";
      }
      enum "TNRD00MPUK70" {
        value 200;
        description
          "TNRD00MPUK70.";
      }
      enum "CX6D0MPUKA90" {
        value 201;
        description
          "CX6D0MPUKA90.";
      }
      enum "CR5D0MPUKA90" {
        value 202;
        description
          "CR5D0MPUKA90.";
      }
      enum "CR2D0MPUEA00" {
        value 203;
        description
          "CR2D0MPUEA00.";
      }
      enum "TNUD0MPUKA90" {
        value 204;
        description
          "TNUD0MPUKA90.";
      }
      enum "CR5D0NPU5070" {
        value 205;
        description
          "CR5D0NPU5070.";
      }
      enum "CX6D0NSU5010" {
        value 206;
        description
          "CX6D0NSU5010.";
      }
      enum "CR2D0NSP5010" {
        value 207;
        description
          "CR2D0NSP5010.";
      }
      enum "CR5DNPU50E70" {
        value 208;
        description
          "CR5DNPU50E70.";
      }
      enum "CR2DNSPE5010" {
        value 209;
        description
          "CR2DNSPE5010.";
      }
      enum "CX6X0PWRDC70" {
        value 210;
        description
          "CX6X0PWRDC70.";
      }
      enum "CX6M001FBX71" {
        value 211;
        description
          "CX6M001FBX71.";
      }
      enum "CX6M002FBX72" {
        value 212;
        description
          "CX6M002FBX72.";
      }
      enum "CX6M002FBX73" {
        value 213;
        description
          "CX6M002FBX73.";
      }
      enum "CX6DNPUI120" {
        value 214;
        description
          "CR5D0NPU120.";
      }
      enum "CR5DNPU12070" {
        value 215;
        description
          "CR5DNPU12070.";
      }
      enum "CX6DNSU12010" {
        value 216;
        description
          "CX6DNSU12010.";
      }
      enum "CR2DNSP12010" {
        value 217;
        description
          "CR2DNSP12010.";
      }
      enum "CR5DNPU1207E" {
        value 218;
        description
          "CR5DNPU1207E.";
      }
      enum "CR2DNSP1201E" {
        value 219;
        description
          "CR2DNSP1201E.";
      }
      enum "CLOCK" {
        value 220;
        description
          "CLOCK.";
      }
      enum "EXTPOWER" {
        value 221;
        description
          "EXTPOWER.";
      }
      enum "POWER" {
        value 222;
        description
          "POWER.";
      }
      enum "POWER DC" {
        value 223;
        description
          "POWER DC.";
      }
      enum "POWER HVDC" {
        value 224;
        description
          "POWER HVDC.";
      }
      enum "POWER AC" {
        value 225;
        description
          "POWER AC.";
      }
      enum "FAN" {
        value 226;
        description
          "FAN.";
      }
      enum "CX67FCBA" {
        value 227;
        description
          "FAN.";
      }
      enum "CX67FCBB" {
        value 228;
        description
          "FAN.";
      }
      enum "CX67FCBB_R" {
        value 229;
        description
          "FAN.";
      }
      enum "CX68FCBC" {
        value 230;
        description
          "FAN.";
      }
      enum "CX68FCBC_NEW" {
        value 231;
        description
          "FAN.";
      }
      enum "CX68FCBD" {
        value 232;
        description
          "FAN.";
      }
      enum "CX68FCBD_R" {
        value 233;
        description
          "FAN.";
      }
      enum "LCD" {
        value 234;
        description
          "LCD.";
      }
      enum "PMU" {
        value 235;
        description
          "PMU.";
      }
      enum "PM" {
        value 236;
        description
          "PM.";
      }
      enum "PEM" {
        value 237;
        description
          "PEM.";
      }
      enum "PDU" {
        value 238;
        description
          "PDU.";
      }
      enum "DMU" {
        value 239;
        description
          "DMU.";
      }
      enum "DACS" {
        value 240;
        description
          "DACS.";
      }
      enum "DE51SRU1A" {
        value 241;
        description
          "DE51SRU1A.";
      }
      enum "DE51SRU1B" {
        value 242;
        description
          "DE51SRU1B.";
      }
      enum "DE51SRU1C" {
        value 243;
        description
          "DE51SRU1C.";
      }
      enum "CR5DSFUIK06A" {
        value 244;
        description
          "CR5DSFUIK06A.";
      }
      enum "CR5D0MPUA550" {
        value 245;
        description
          "CR5D0MPUA550.";
      }
      enum "CR5D00ICUB50" {
        value 246;
        description
          "CR5D00ICUB50.";
      }
      enum "CR5DSFUFK050" {
        value 247;
        description
          "CR5DSFUFK050.";
      }
      enum "CR5D0MPUA451" {
        value 248;
        description
          "CR5D0MPUA451.";
      }
      enum "CR5D00ICUA51" {
        value 249;
        description
          "CR5D00ICUA51.";
      }
      enum "CR5DSFUFK051" {
        value 250;
        description
          "CR5DSFUFK051.";
      }
      enum "CR5DSFUFT050" {
        value 251;
        description
          "CR5DSFUFT050.";
      }
      enum "CR5DSFUIT06H" {
        value 252;
        description
          "CR5DSFUIT06H.";
      }
      enum "CR5D0MPUA750" {
        value 253;
        description
          "CR5D0MPUA750.";
      }
      enum "CR5D0MPUB660" {
        value 254;
        description
          "CR5D0MPUB660.";
      }
      enum "CR5D0MPUB680" {
        value 255;
        description
          "CR5D0MPUB680.";
      }
      enum "CR5DSFUIK06B" {
        value 256;
        description
          "CR5DSFUIK06B.";
      }
      enum "CR5DSFUIK06C" {
        value 257;
        description
          "CR5DSFUIK06C.";
      }
      enum "CR9D0MPUN180" {
        value 258;
        description
          "CR9D0MPUN180.";
      }
      enum "CR9D00E8NC80" {
        value 259;
        description
          "CR9D00E8NC80.";
      }
      enum "CR9D00EFMB80" {
        value 260;
        description
          "CR9D00EFMB80.";
      }
      enum "CR9D0SFUTF80" {
        value 261;
        description
          "CR9D0SFUTF80.";
      }
      enum "CR9D0MPUP180" {
        value 262;
        description
          "CR9D0MPUP180.";
      }
      enum "CR9D0SFUT481" {
        value 263;
        description
          "CR9D0SFUT481.";
      }
      enum "CR9D0SFUT48D" {
        value 264;
        description
          "CR9D0SFUT48D.";
      }
      enum "CR9D0SFUT48E" {
        value 265;
        description
          "CR9D0SFUT48E.";
      }
      enum "CR9D0SFUT280" {
        value 266;
        description
          "CR9D0SFUT280.";
      }
      enum "CX6D0MPUP1A0" {
        value 267;
        description
          "CX6D0MPUP1A0.";
      }
      enum "CX6D0MPUP2A0" {
        value 268;
        description
          "CX6D0MPUP2A0.";
      }
      enum "CX6DSFUIT4AA" {
        value 269;
        description
          "CX6DSFUIT4AA.";
      }
      enum "CX6D0MPUN1A0" {
        value 270;
        description
          "CX6D0MPUN1A0.";
      }
      enum "CX6DSFUIT4AB" {
        value 271;
        description
          "CX6DSFUIT4AB.";
      }
      enum "CR9D0SFUT480" {
        value 272;
        description
          "CR9D0SFUT480.";
      }
      enum "CR9D00EPXF80" {
        value 273;
        description
          "CR9D00EPXF80.";
      }
      enum "CR9D00EDNB80" {
        value 274;
        description
          "CR9D00EDNB80.";
      }
      enum "CR9D000CMU60" {
        value 275;
        description
          "CR9D000CMU60.";
      }
      enum "CR9D00D8NC80" {
        value 276;
        description
          "CR9D00D8NC80.";
      }
      enum "CR5DLPUFK061" {
        value 277;
        description
          "CR5DLPUFK061.";
      }
      enum "CR5D00LMXF61" {
        value 278;
        description
          "CR5D00LMXF61.";
      }
      enum "CR5D00LAXF60" {
        value 279;
        description
          "CR5D00LAXF60.";
      }
      enum "CR5D0MPUB560" {
        value 280;
        description
          "CR5D0MPUB560.";
      }
      enum "CR57LPUF120A" {
        value 281;
        description
          "CR57LPUF120A.";
      }
      enum "CR57LPUF240A" {
        value 282;
        description
          "CR57LPUF240A.";
      }
      enum "CR57LPUF480B" {
        value 283;
        description
          "CR57LPUF480B.";
      }
      enum "CR57SRU200A" {
        value 284;
        description
          "CR57SRU200A.";
      }
      enum "CR57SFU200C" {
        value 285;
        description
          "CR57SFU200C.";
      }
      enum "CR57FRA200A" {
        value 286;
        description
          "CR57FRA200A.";
      }
      enum "CR57SFU200B" {
        value 287;
        description
          "CR57SFU200B.";
      }
      enum "CR5DLPUFB070" {
        value 288;
        description
          "CR5DLPUFB070.";
      }
      enum "CR5DLPUFB07B" {
        value 289;
        description
          "CR5DLPUFB07B.";
      }
      enum "CR5DLPUFF070" {
        value 290;
        description
          "CR5DLPUFF070.";
      }
      enum "CR5DLPUFF080" {
        value 291;
        description
          "CR5DLPUFF080.";
      }
      enum "CR5DLPUFF07B" {
        value 292;
        description
          "CR5DLPUFF07B.";
      }
      enum "CR5DSFUIE07B" {
        value 293;
        description
          "CR5DSFUIE07B.";
      }
      enum "CR5DSFUIE07D" {
        value 294;
        description
          "CR5DSFUIE07D.";
      }
      enum "CR5D0MPUB570" {
        value 295;
        description
          "CR5D0MPUB570.";
      }
      enum "CX6D0MPUB570" {
        value 296;
        description
          "CX6D0MPUB570.";
      }
      enum "CR5D0SRUA970" {
        value 297;
        description
          "CR5D0SRUA970.";
      }
      enum "CR5D0SRUA870" {
        value 298;
        description
          "CR5D0SRUA870.";
      }
      enum "CX6D0SRUA970" {
        value 299;
        description
          "CX6D0SRUA970.";
      }
      enum "CX6D0SRUA870" {
        value 300;
        description
          "CX6D0SRUA870.";
      }
      enum "CR5D00E8NC70" {
        value 301;
        description
          "CR5D00E8NC70.";
      }
      enum "CR5D00E8NC7B" {
        value 302;
        description
          "CR5D00E8NC7B.";
      }
      enum "CR5DLPUF517E" {
        value 303;
        description
          "CR5DLPUF517E.";
      }
      enum "CR5D0EMGFA7J" {
        value 304;
        description
          "CR5D0EMGFA7J.";
      }
      enum "CR5DL2XEFG7J" {
        value 305;
        description
          "CR5DL2XEFG7J.";
      }
      enum "CR5DSFUIU07C" {
        value 306;
        description
          "CR5DSFUIU07C.";
      }
      enum "CR5DSFUIM07C" {
        value 307;
        description
          "CR5DSFUIM07C.";
      }
      enum "CX6DSFUIU07C" {
        value 308;
        description
          "CX6DSFUIU07C.";
      }
      enum "CX6DSFUIM07C" {
        value 309;
        description
          "CX6DSFUIM07C.";
      }
      enum "CR5DSFUIU07B" {
        value 310;
        description
          "CR5DSFUIU07B.";
      }
      enum "CR5DSFUIM07B" {
        value 311;
        description
          "CR5DSFUIM07B.";
      }
      enum "CX6DSFUIU07B" {
        value 312;
        description
          "CX6DSFUIU07B.";
      }
      enum "CX6DSFUIM07B" {
        value 313;
        description
          "CX6DSFUIM07B.";
      }
      enum "CR57FRA1TA" {
        value 314;
        description
          "CR57FRA1TA.";
      }
      enum "CR5D0LBXFA70" {
        value 315;
        description
          "CR5D0LBXFA70.";
      }
      enum "CR5D0E2MCA70" {
        value 316;
        description
          "CR5D0E2MCA70.";
      }
      enum "CR5D00E1NC76" {
        value 317;
        description
          "CR5D00E1NC76.";
      }
      enum "CR5D00E1NC78" {
        value 318;
        description
          "CR5D00E1NC78.";
      }
      enum "CR5D00E1ND71" {
        value 319;
        description
          "CR5D00E1ND71.";
      }
      enum "CR5D00E1ND72" {
        value 320;
        description
          "CR5D00E1ND72.";
      }
      enum "CR5D0LBXFA7B" {
        value 321;
        description
          "CR5D0LBXFA7B.";
      }
      enum "CR5D0E2MCA7B" {
        value 322;
        description
          "CR5D0E2MCA7B.";
      }
      enum "CR5D00E1NC7B" {
        value 323;
        description
          "CR5D00E1NC7B.";
      }
      enum "CR5D00E1NC7C" {
        value 324;
        description
          "CR5D00E1NC7C.";
      }
      enum "CR5D00E2NC70" {
        value 325;
        description
          "CR5D00E2NC70.";
      }
      enum "CR5D00E2NC71" {
        value 326;
        description
          "CR5D00E2NC71.";
      }
      enum "CR5DL6XE8G70" {
        value 327;
        description
          "CR5DL6XE8G70.";
      }
      enum "ME0DL6XE8G70" {
        value 328;
        description
          "ME0DL6XE8G70.";
      }
      enum "CR5D00E2ND70" {
        value 329;
        description
          "CR5D00E2ND70.";
      }
      enum "CR5DE1NLBX72" {
        value 330;
        description
          "CR5DE1NLBX72.";
      }
      enum "CR5D00E2ND71" {
        value 331;
        description
          "CR5D00E2ND71.";
      }
      enum "CR5DE1NLBX73" {
        value 332;
        description
          "CR5DE1NLBX73.";
      }
      enum "ME0D0E2NBB70" {
        value 333;
        description
          "ME0D0E2NBB70.";
      }
      enum "CR5D00LFXF70" {
        value 334;
        description
          "CR5D00LFXF70.";
      }
      enum "CR5DE2NLBX70" {
        value 335;
        description
          "CR5DE2NLBX70.";
      }
      enum "CR5DE1NLBX70" {
        value 336;
        description
          "CR5DE1NLBX70.";
      }
      enum "CR5D00E2NC73" {
        value 337;
        description
          "CR5D00E2NC73.";
      }
      enum "CR5D00E2NC74" {
        value 338;
        description
          "CR5D00E2NC74.";
      }
      enum "CR5D00LFXF73" {
        value 339;
        description
          "CR5D00LFXF73.";
      }
      enum "CR5DE2NLBX73" {
        value 340;
        description
          "CR5DE2NLBX73.";
      }
      enum "CR5DE1NLBX71" {
        value 341;
        description
          "CR5DE1NLBX71.";
      }
      enum "CR5DSFUIE07C" {
        value 342;
        description
          "CR5DSFUIE07C.";
      }
      enum "CX6DSFUIE01C" {
        value 343;
        description
          "CX6DSFUIE01C.";
      }
      enum "CR5D0SRUA570" {
        value 344;
        description
          "CR5D0SRUA570.";
      }
      enum "CX6D0SRUA510" {
        value 345;
        description
          "CX6D0SRUA510.";
      }
      enum "CR5D0MPUB460" {
        value 346;
        description
          "CR5D0MPUB460.";
      }
      enum "CX6D0MPUB410" {
        value 347;
        description
          "CX6D0MPUB410.";
      }
      enum "CR5DLPUFM070" {
        value 348;
        description
          "CR5DLPUFM070.";
      }
      enum "CR5D00LMXF70" {
        value 349;
        description
          "CR5D00LMXF70.";
      }
      enum "CR5DE2NLFX70" {
        value 350;
        description
          "CR5DE2NLFX70.";
      }
      enum "CR5D00E4NC70" {
        value 351;
        description
          "CR5D00E4NC70.";
      }
      enum "CR5D00D4NC70" {
        value 352;
        description
          "CR5D00D4NC70.";
      }
      enum "CR5D00D8NC70" {
        value 353;
        description
          "CR5D00D8NC70.";
      }
      enum "CR5D00EENB70" {
        value 354;
        description
          "CR5D00EENB70.";
      }
      enum "ANKD001EV106" {
        value 355;
        description
          "ANKD001EV106.";
      }
      enum "CR5D00EENB7B" {
        value 356;
        description
          "CR5D00EENB7B.";
      }
      enum "CR5D00EENB7P" {
        value 357;
        description
          "CR5D00EENB7P.";
      }
      enum "CR5D0SRUA872" {
        value 358;
        description
          "CR5D0SRUA872.";
      }
      enum "CR5DSFUIM17C" {
        value 359;
        description
          "CR5DSFUIM17C.";
      }
      enum "CR5DSFUIM17B" {
        value 360;
        description
          "CR5DSFUIM17B.";
      }
      enum "CX6DSFUIM17B" {
        value 361;
        description
          "CX6DSFUIM17B.";
      }
      enum "CX6DSFUIT27B" {
        value 362;
        description
          "CX6DSFUIT27B.";
      }
      enum "CX6D0SRUA872" {
        value 363;
        description
          "CX6D0SRUA872.";
      }
      enum "CX6DSFUIM17C" {
        value 364;
        description
          "CX6DSFUIM17C.";
      }
      enum "TNRDSFUIM17B" {
        value 365;
        description
          "TNRDSFUIM17B.";
      }
      enum "TNRDSFUIT27B" {
        value 366;
        description
          "TNRDSFUIT27B.";
      }
      enum "TNRD0SRUA872" {
        value 367;
        description
          "TNRD0SRUA872.";
      }
      enum "TNRDSFUIM17C" {
        value 368;
        description
          "TNRDSFUIM17C.";
      }
      enum "CX6DSFUIM11B" {
        value 369;
        description
          "CX6DSFUIM11B.";
      }
      enum "CX6D0SRUA812" {
        value 370;
        description
          "CX6D0SRUA812.";
      }
      enum "CX6DSFUIM11C" {
        value 371;
        description
          "CX6DSFUIM11C.";
      }
      enum "ME0DSFUIM17B" {
        value 372;
        description
          "ME0DSFUIM17B.";
      }
      enum "ME0D0SRUA872" {
        value 373;
        description
          "ME0D0SRUA872.";
      }
      enum "ME0DSFUIM17C" {
        value 374;
        description
          "ME0DSFUIM17C.";
      }
      enum "CR5D0SRUAA70" {
        value 375;
        description
          "CR5D0SRUAA70.";
      }
      enum "CR5DSFUIU07D" {
        value 376;
        description
          "CR5DSFUIU07D.";
      }
      enum "CR5DSFUIT27E" {
        value 377;
        description
          "CR5DSFUIT27E.";
      }
      enum "CR5DSFUIU07F" {
        value 378;
        description
          "CR5DSFUIU07F.";
      }
      enum "CX6DSFUIU07F" {
        value 379;
        description
          "CX6DSFUIU07F.";
      }
      enum "CX6DSFUIT27E" {
        value 380;
        description
          "CX6DSFUIT27E.";
      }
      enum "TNRDSFUIU07F" {
        value 381;
        description
          "TNRDSFUIU07F.";
      }
      enum "TNRDSFUIT27E" {
        value 382;
        description
          "TNRDSFUIT27E.";
      }
      enum "CX6D0SRUAA70" {
        value 383;
        description
          "CX6D0SRUAA70.";
      }
      enum "CX6DSFUIU07D" {
        value 384;
        description
          "CX6DSFUIU07D.";
      }
      enum "TNRD0SRUAA70" {
        value 385;
        description
          "TNRD0SRUAA70.";
      }
      enum "TNRDSFUIU07D" {
        value 386;
        description
          "TNRDSFUIU07D.";
      }
      enum "CR5DLPUFME70" {
        value 387;
        description
          "CR5DLPUFME70.";
      }
      enum "CR5D00E4NC7P" {
        value 388;
        description
          "CR5D00E4NC7P.";
      }
      enum "ME0DBSUFM070" {
        value 389;
        description
          "ME0DBSUFM070.";
      }
      enum "ME0DMSUFM070" {
        value 390;
        description
          "ME0DMSUFM070.";
      }
      enum "CR5DE2NLFX71" {
        value 391;
        description
          "CR5DE2NLFX71.";
      }
      enum "CR5DLPUFF17E" {
        value 392;
        description
          "CR5DLPUFF17E.";
      }
      enum "CR5DLPUFF17Q" {
        value 393;
        description
          "CR5DLPUFF17Q.";
      }
      enum "ME0DBSUFF073" {
        value 394;
        description
          "ME0DBSUFF073.";
      }
      enum "ME0DBSUFF072" {
        value 395;
        description
          "ME0DBSUFF072.";
      }
      enum "CR5DE2NLFX72" {
        value 396;
        description
          "CR5DE2NLFX72.";
      }
      enum "CR5DE2NLFX73" {
        value 397;
        description
          "CR5DE2NLFX73.";
      }
      enum "CR5D00E4NB70" {
        value 398;
        description
          "CR5D00E4NB70.";
      }
      enum "CR5D00E4NB7B" {
        value 399;
        description
          "CR5D00E4NB7B.";
      }
      enum "CR5D00E4NB7C" {
        value 400;
        description
          "CR5D00E4NB7C.";
      }
      enum "ME0DE2NLEX7C" {
        value 401;
        description
          "ME0DE2NLEX7C.";
      }
      enum "ME0D0E4NBM70" {
        value 402;
        description
          "ME0D0E4NBM70.";
      }
      enum "CX6DSFUIE01B" {
        value 403;
        description
          "CX6DSFUIE01B.";
      }
      enum "fname8090CX600-X8" {
        value 404;
        description
          "CX600-X8 chassis.";
      }
      enum "fname8090CX600-X16" {
        value 405;
        description
          "CX600-X16 chassis.";
      }
      enum "CR5DSFUIT060" {
        value 406;
        description
          "CR5DSFUIT060.";
      }
      enum "CR5DSFUIT06E" {
        value 407;
        description
          "CR5DSFUIT06E.";
      }
      enum "CR5DSFUIT26A" {
        value 408;
        description
          "CR5DSFUIT26A.";
      }
      enum "CR5DSFUIT16E" {
        value 409;
        description
          "CR5DSFUIT16E.";
      }
      enum "CR5D00E8NC61" {
        value 410;
        description
          "CR5D00E8NC61.";
      }
      enum "CR5D00E8NC80" {
        value 411;
        description
          "CR5D00E8NC80.";
      }
      enum "CR5DE8NEDX61" {
        value 412;
        description
          "CR5DE8NEDX61.";
      }
      enum "CR5D00EDNB60" {
        value 413;
        description
          "CR5D00EDNB60.";
      }
      enum "CR5DEDNLIX60" {
        value 414;
        description
          "CR5DEDNLIX60.";
      }
      enum "CR5DLPUFT060" {
        value 415;
        description
          "CR5DLPUFT060.";
      }
      enum "CR5D00EFMB60" {
        value 416;
        description
          "CR5D00EFMB60.";
      }
      enum "CR5D00E8NC60" {
        value 417;
        description
          "CR5D00E8NC60.";
      }
      enum "CR5DSFU0K06B" {
        value 418;
        description
          "CR5DSFU0K06B.";
      }
      enum "CR5D0SRUB060" {
        value 419;
        description
          "CR5D0SRUB060.";
      }
      enum "CR56SRUB1TA" {
        value 420;
        description
          "CR56SRUB1TA.";
      }
      enum "CR5D0SFUT061" {
        value 421;
        description
          "CR5D0SFUT061.";
      }
      enum "CR56SFU1TC" {
        value 422;
        description
          "CR56SFU1TC.";
      }
      enum "CR56FRA1TA" {
        value 423;
        description
          "CR56FRA1TA.";
      }
      enum "CR5D0MPUC061" {
        value 424;
        description
          "CR5D0MPUC061.";
      }
      enum "CR5DLPUFK062" {
        value 425;
        description
          "CR5DLPUFK062.";
      }
      enum "CR5D00N8NC60" {
        value 426;
        description
          "CR5D00N8NC60.";
      }
      enum "CR5D00N8NC61" {
        value 427;
        description
          "CR5D00N8NC61.";
      }
      enum "CR5D00L4NC60" {
        value 428;
        description
          "CR5D00L4NC60.";
      }
      enum "CR5D00LKXF60" {
        value 429;
        description
          "CR5D00LKXF60.";
      }
      enum "CR5DL2NLEX60" {
        value 430;
        description
          "CR5DL2NLEX60.";
      }
      enum "CR5DE2NLEX80" {
        value 431;
        description
          "CR5DE2NLEX80.";
      }
      enum "CR5DNPU24070" {
        value 432;
        description
          "CR5DNPU24070.";
      }
      enum "CR5DNPU24071" {
        value 433;
        description
          "CR5DNPU24071.";
      }
      enum "CR2DNSPA0010" {
        value 434;
        description
          "CR2DNSPA0010.";
      }
      enum "CR2DNSPB0010" {
        value 435;
        description
          "CR2DNSPB0010.";
      }
      enum "CR5DNPU48070" {
        value 436;
        description
          "CR5DNPU48070.";
      }
      enum "CR2DNSPC0010" {
        value 437;
        description
          "CR2DNSPC0010.";
      }
      enum "CR5DNPU1TM70" {
        value 438;
        description
          "CR5DNPU1TM70.";
      }
      enum "CR5DNPU1TM71" {
        value 439;
        description
          "CR5DNPU1TM71.";
      }
      enum "CX6DNPU1TM70" {
        value 440;
        description
          "CX6DNPU1TM70.";
      }
      enum "CR2DNSPD0010" {
        value 441;
        description
          "CR2DNSPD0010.";
      }
      enum "CX6D00MPUK11" {
        value 442;
        description
          "CX6D00MPUK11.";
      }
      enum "CX6D0MPUK170" {
        value 443;
        description
          "CX6D0MPUK170.";
      }
      enum "ME0D0MPUK171" {
        value 444;
        description
          "ME0D0MPUK171.";
      }
      enum "CR5D0MPUK170" {
        value 445;
        description
          "CR5D0MPUK170.";
      }
      enum "TNUD00MPUK71" {
        value 446;
        description
          "TNUD00MPUK71.";
      }
      enum "CR2D0MPUE110" {
        value 447;
        description
          "CR2D0MPUE110.";
      }
      enum "CR5DLPUF5070" {
        value 448;
        description
          "CR5DLPUF5070.";
      }
      enum "CR5DLPUF5170" {
        value 449;
        description
          "CR5DLPUF5170.";
      }
      enum "CR5DLPUF517B" {
        value 450;
        description
          "CR5DLPUF517B.";
      }
      enum "CR5D0L5XFA71" {
        value 451;
        description
          "CR5D0L5XFA71.";
      }
      enum "CR5D0L4XFA70" {
        value 452;
        description
          "CR5D0L4XFA70.";
      }
      enum "CR5D0EMGFA70" {
        value 453;
        description
          "CR5D0EMGFA70.";
      }
      enum "CR5DL2XEFG7A" {
        value 454;
        description
          "CR5DL2XEFG7A.";
      }
      enum "CR5DL3XEFG7C" {
        value 455;
        description
          "CR5DL3XEFG7C.";
      }
      enum "CR5D0L5XFA7B" {
        value 456;
        description
          "CR5D0L5XFA7B.";
      }
      enum "CR5D0L4XFA7B" {
        value 457;
        description
          "CR5D0L4XFA7B.";
      }
      enum "CR5D0EMGFA7B" {
        value 458;
        description
          "CR5D0EMGFA7B.";
      }
      enum "CR5DL2XEFG7B" {
        value 459;
        description
          "CR5DL2XEFG7B.";
      }
      enum "CR5D00L5XF72" {
        value 460;
        description
          "CR5D00L5XF72.";
      }
      enum "CR5D00L4XF71" {
        value 461;
        description
          "CR5D00L4XF71.";
      }
      enum "CR5D00EMGF73" {
        value 462;
        description
          "CR5D00EMGF73.";
      }
      enum "CR5DL2XEFG72" {
        value 463;
        description
          "CR5DL2XEFG72.";
      }
      enum "CR5D0L5XFA7L" {
        value 464;
        description
          "CR5D0L5XFA7L.";
      }
      enum "CR5DL2XEIG7L" {
        value 465;
        description
          "CR5DL2XEIG7L.";
      }
      enum "CR5D0EMGFA7L" {
        value 466;
        description
          "CR5D0EMGFA7L.";
      }
      enum "CR5DLPUFA071" {
        value 467;
        description
          "CR5DLPUFA071.";
      }
      enum "CR5DLPUFA07B" {
        value 468;
        description
          "CR5DLPUFA07B.";
      }
      enum "CR5D00E2MC70" {
        value 469;
        description
          "CR5D00E2MC70.";
      }
      enum "CR5D0LAXFA71" {
        value 470;
        description
          "CR5D0LAXFA71.";
      }
      enum "CR5D00E1NC72" {
        value 471;
        description
          "CR5D00E1NC72.";
      }
      enum "CR5D00E2MC7B" {
        value 472;
        description
          "CR5D00E2MC7B.";
      }
      enum "CR5D0LAXFA7B" {
        value 473;
        description
          "CR5D0LAXFA7B.";
      }
      enum "CR5D00E2MC71" {
        value 474;
        description
          "CR5D00E2MC71.";
      }
      enum "CR5D0LAXFA72" {
        value 475;
        description
          "CR5D0LAXFA72.";
      }
      enum "CR5D00E1NC73" {
        value 476;
        description
          "CR5D00E1NC73.";
      }
      enum "ME0DBSUFA070" {
        value 477;
        description
          "ME0DBSUFA070.";
      }
      enum "ME0DBSUFF070" {
        value 478;
        description
          "ME0DBSUFF070.";
      }
      enum "CR5DLPUFB07E" {
        value 479;
        description
          "CR5DLPUFB07E.";
      }
      enum "CR5DLPUFF07E" {
        value 480;
        description
          "CR5DLPUFF07E.";
      }
      enum "ME0DMSUFA070" {
        value 481;
        description
          "ME0DMSUFA070.";
      }
      enum "ME0DMSUF5170" {
        value 482;
        description
          "ME0DMSUF5170.";
      }
      enum "ME0DBSUF5170" {
        value 483;
        description
          "ME0DBSUF5170.";
      }
      enum "CR5DLPUF507L" {
        value 484;
        description
          "CR5DLPUF507L.";
      }
      enum "CR5DL4XEBG7L" {
        value 485;
        description
          "CR5DL4XEBG7L.";
      }
      enum "CR5D0L5XFA7J" {
        value 486;
        description
          "CR5D0L5XFA7J.";
      }
      enum "CR5D00LBXF7L" {
        value 487;
        description
          "CR5D00LBXF7L.";
      }
      enum "CR5D00L5XF73" {
        value 488;
        description
          "CR5D00L5XF73.";
      }
      enum "CR5D00EMGF74" {
        value 489;
        description
          "CR5D00EMGF74.";
      }
      enum "CR5DL2XEFG73" {
        value 490;
        description
          "CR5DL2XEFG73.";
      }
      enum "CR5DLPUFA07J" {
        value 491;
        description
          "CR5DLPUFA07J.";
      }
      enum "CR5DLPUFA27E" {
        value 492;
        description
          "CR5DLPUFA27E.";
      }
      enum "CR5D00LFXF7L" {
        value 493;
        description
          "CR5D00LFXF7L.";
      }
      enum "CR5D00TBXF71" {
        value 494;
        description
          "CR5D00TBXF71.";
      }
      enum "CR5D00TFXF71" {
        value 495;
        description
          "CR5D00TFXF71.";
      }
      enum "CR5D0MPUD170" {
        value 496;
        description
          "CR5D0MPUD170.";
      }
      enum "CR5D0MPUD270" {
        value 497;
        description
          "CR5D0MPUD270.";
      }
      enum "CX6D0MPUD170" {
        value 498;
        description
          "CX6D0MPUD170.";
      }
      enum "CX6D0MPUD270" {
        value 499;
        description
          "CX6D0MPUD270.";
      }
      enum "TNRD0MPUD270" {
        value 500;
        description
          "TNRD0MPUD270.";
      }
      enum "TNRD0MPUD370" {
        value 501;
        description
          "TNRD0MPUD370.";
      }
      enum "ME0D00MPUD71" {
        value 502;
        description
          "ME0D00MPUD71.";
      }
      enum "ME0D00MPUD72" {
        value 503;
        description
          "ME0D00MPUD72.";
      }
      enum "CR5D0MPUD470" {
        value 504;
        description
          "CR5D0MPUD470.";
      }
      enum "CX6D0MPUD470" {
        value 505;
        description
          "CX6D0MPUD470.";
      }
      enum "TNRD0MPUD470" {
        value 506;
        description
          "TNRD0MPUD470.";
      }
      enum "ME0P0MPUD470" {
        value 507;
        description
          "ME0P0MPUD470.";
      }
      enum "CR5D00D2NT70" {
        value 508;
        description
          "CR5D00D2NT70.";
      }
      enum "CR5DLPUFE070" {
        value 509;
        description
          "CR5DLPUFE070.";
      }
      enum "TNRD0SRUA870" {
        value 510;
        description
          "TNRD0SRUA870.";
      }
      enum "TNRDSFUIM07C" {
        value 511;
        description
          "TNRDSFUIM07C.";
      }
      enum "TNRD0SRUA970" {
        value 512;
        description
          "TNRD0SRUA970.";
      }
      enum "TNRDSFUIU07C" {
        value 513;
        description
          "TNRDSFUIU07C.";
      }
      enum "CR5DSFUIT27B" {
        value 514;
        description
          "CR5DSFUIT27B.";
      }
      enum "ME0D0SRUA870" {
        value 515;
        description
          "ME0D0SRUA870.";
      }
      enum "ME0D0SRUA970" {
        value 516;
        description
          "ME0D0SRUA970.";
      }
      enum "ME0DSFUIU07C" {
        value 517;
        description
          "ME0DSFUIU07C.";
      }
      enum "ME0DSFUIK07B" {
        value 518;
        description
          "ME0DSFUIK07B.";
      }
      enum "TNRD0MPUB470" {
        value 519;
        description
          "TNRD0MPUB470.";
      }
      enum "TNRD0MPUB570" {
        value 520;
        description
          "TNRD0MPUB570.";
      }
      enum "TNRDSFUIE07B" {
        value 521;
        description
          "TNRDSFUIE07B.";
      }
      enum "ME0D0MPUB570" {
        value 522;
        description
          "ME0D0MPUB570.";
      }
      enum "ME0DSFUIE07B" {
        value 523;
        description
          "ME0DSFUIE07B.";
      }
      enum "TNRD0SRUA570" {
        value 524;
        description
          "TNRD0SRUA570.";
      }
      enum "TNRDSFUIE07C" {
        value 525;
        description
          "TNRDSFUIE07C.";
      }
      enum "TNRDSFUIM07B" {
        value 526;
        description
          "TNRDSFUIM07B.";
      }
      enum "TNRDSFUIU07B" {
        value 527;
        description
          "TNRDSFUIU07B.";
      }
      enum "ME0DSFUIU07B" {
        value 528;
        description
          "ME0DSFUIU07B.";
      }
      enum "ME0DSFUIK07A" {
        value 529;
        description
          "ME0DSFUIK07A.";
      }
      enum "ME0D0MPUB470" {
        value 530;
        description
          "ME0D0MPUB470.";
      }
      enum "ME0DSFUIE07D" {
        value 531;
        description
          "ME0DSFUIE07D.";
      }
      enum "ME0D0SRUA570" {
        value 532;
        description
          "ME0D0SRUA570.";
      }
      enum "ME0DSFUIE07C" {
        value 533;
        description
          "ME0DSFUIE07C.";
      }
      enum "CR5DVSUF8010" {
        value 534;
        description
          "CR5DVSUF8010.";
      }
      enum "ME0DVSUF8070" {
        value 535;
        description
          "ME0DVSUF8070.";
      }
      enum "ME0DVSUF8071" {
        value 536;
        description
          "ME0DVSUF8071.";
      }
      enum "ME0DVSUFD071" {
        value 537;
        description
          "ME0DVSUFD071.";
      }
      enum "CR5DVSUFD010" {
        value 538;
        description
          "CR5DVSUFD010.";
      }
      enum "ME0DVSUFD070" {
        value 539;
        description
          "ME0DVSUFD070.";
      }
      enum "CX6B0BKP0371" {
        value 540;
        description
          "CX6B0BKP0371.";
      }
      enum "CX6B0BKP0372" {
        value 541;
        description
          "CX6B0BKP0372.";
      }
      enum "CR5B0BKP0371" {
        value 542;
        description
          "CR5B0BKP0371.";
      }
      enum "CR5B0BKP0372" {
        value 543;
        description
          "CR5B0BKP0372.";
      }
      enum "CR2B0BKP0210" {
        value 544;
        description
          "CR2B0BKP0210.";
      }
      enum "CR2B0BKP0211" {
        value 545;
        description
          "CR2B0BKP0211.";
      }
      enum "TNRB0BKP0371" {
        value 546;
        description
          "TNRB0BKP0371.";
      }
      enum "TNRB0BKP0372" {
        value 547;
        description
          "TNRB0BKP0372.";
      }
      enum "CR5DVSUID010" {
        value 548;
        description
          "CR5DVSUID010.";
      }
      enum "ME0DVSUID070" {
        value 549;
        description
          "ME0DVSUID070.";
      }
      enum "ME0D0VSE0070" {
        value 550;
        description
          "ME0D0VSE0070.";
      }
      enum "ME0DVSUF8072" {
        value 551;
        description
          "ME0DVSUF8072.";
      }
      enum "ME0DVSUF8073" {
        value 552;
        description
          "ME0DVSUF8073.";
      }
      enum "CR5DVSUF8011" {
        value 553;
        description
          "CR5DVSUF8011.";
      }
      enum "CR5D0EMGFA7P" {
        value 554;
        description
          "CR5D0EMGFA7P.";
      }
      enum "CR5D00LBXF7P" {
        value 555;
        description
          "CR5D00LBXF7P.";
      }
      enum "CR5DL6XEFG7P" {
        value 556;
        description
          "CR5DL6XEFG7P.";
      }
      enum "CR5D00LFXF7P" {
        value 557;
        description
          "CR5D00LFXF7P.";
      }
      enum "CR5D00E8NC7P" {
        value 558;
        description
          "CR5D00E8NC7P.";
      }
      enum "CX6D0L5XFA1B" {
        value 559;
        description
          "CX6D0L5XFA1B.";
      }
      enum "CX6D0EMGFA1B" {
        value 560;
        description
          "CX6D0EMGFA1B.";
      }
      enum "CX6DISUFA110" {
        value 561;
        description
          "CX6DISUFA110.";
      }
      enum "CX6DISUFA210" {
        value 562;
        description
          "CX6DISUFA210.";
      }
      enum "CX6DISUFB010" {
        value 563;
        description
          "CX6DISUFB010.";
      }
      enum "CX6D0LAXFA10" {
        value 564;
        description
          "CX6D0LAXFA10.";
      }
      enum "CX6D0LBXFA11" {
        value 565;
        description
          "CX6D0LBXFA11.";
      }
      enum "CR5DLAXFAJ7E" {
        value 566;
        description
          "CR5DLAXFAJ7E.";
      }
      enum "CR5DL2XEFG7E" {
        value 567;
        description
          "CR5DL2XEFG7E.";
      }
      enum "CX6DISUFE012" {
        value 568;
        description
          "CX6DISUFE012.";
      }
      enum "CX6DISUFE013" {
        value 569;
        description
          "CX6DISUFE013.";
      }
      enum "CX6DISUFE011" {
        value 570;
        description
          "CX6DISUFE011.";
      }
      enum "CX6DISUFF010" {
        value 571;
        description
          "CX6DISUFF010.";
      }
      enum "CX6D0LFXFA10" {
        value 572;
        description
          "CX6D0LFXFA10.";
      }
      enum "CX6DISUF5110" {
        value 573;
        description
          "CX6DISUF5110.";
      }
      enum "CX6DISUF511B" {
        value 574;
        description
          "CX6DISUF511B.";
      }
      enum "CX6DSFUIE07C" {
        value 575;
        description
          "CX6DSFUIE07C.";
      }
      enum "CX6DSFUIA07D" {
        value 576;
        description
          "CX6DSFUIA07D.";
      }
      enum "CX6D0SRUA511" {
        value 577;
        description
          "CX6D0SRUA511.";
      }
      enum "CX6D0SRUA770" {
        value 578;
        description
          "CX6D0SRUA770.";
      }
      enum "CX6D0LEXFA10" {
        value 579;
        description
          "CX6D0LEXFA10.";
      }
      enum "CX6DSFUIE07B" {
        value 580;
        description
          "CX6DSFUIE07B.";
      }
      enum "CR5D0SRUA770" {
        value 581;
        description
          "CR5D0SRUA770.";
      }
      enum "CX6D0MPUB411" {
        value 582;
        description
          "CX6D0MPUB411.";
      }
      enum "CR5D0SRUB570" {
        value 583;
        description
          "CR5D0SRUB570.";
      }
      enum "CR5D0SRUB571" {
        value 584;
        description
          "CR5D0SRUB571.";
      }
      enum "CX6D0SRUB510" {
        value 585;
        description
          "CX6D0SRUB510.";
      }
      enum "ME0D0SRUB570" {
        value 586;
        description
          "ME0D0SRUB570.";
      }
      enum "TNRD0SRUB570" {
        value 587;
        description
          "TNRD0SRUB570.";
      }
      enum "CX6DISUFM010" {
        value 588;
        description
          "CX6DISUFM010.";
      }
      enum "CR5DSFUIA07D" {
        value 589;
        description
          "CR5DSFUIA07D.";
      }
      enum "CR5DLPUFM07B" {
        value 590;
        description
          "CR5DLPUFM07B.";
      }
      enum "CR5DLPUFME71" {
        value 591;
        description
          "CR5DLPUFME71.";
      }
      enum "CR5DLPUFK071" {
        value 592;
        description
          "CR5DLPUFK071.";
      }
      enum "CR5DLPUFM071" {
        value 593;
        description
          "CR5DLPUFM071.";
      }
      enum "CR5DLPUFM17B" {
        value 594;
        description
          "CR5DLPUFM17B.";
      }
      enum "CR5D00LMXF71" {
        value 595;
        description
          "CR5D00LMXF71.";
      }
      enum "CR5DE2NLFX74" {
        value 596;
        description
          "CR5DE2NLFX74.";
      }
      enum "CR5D00E4NC71" {
        value 597;
        description
          "CR5D00E4NC71.";
      }
      enum "CR5D01LMXF7B" {
        value 598;
        description
          "CR5D01LMXF7B.";
      }
      enum "CR5DE2NLFX75" {
        value 599;
        description
          "CR5DE2NLFX75.";
      }
      enum "CR5D01E4NC7B" {
        value 600;
        description
          "CR5D01E4NC7B.";
      }
      enum "CR5D01LMXF7C" {
        value 601;
        description
          "CR5D01LMXF7C.";
      }
      enum "CR5DE2NLFX76" {
        value 602;
        description
          "CR5DE2NLFX76.";
      }
      enum "CR5D01E4NC7C" {
        value 603;
        description
          "CR5D01E4NC7C.";
      }
      enum "CR5D00D4NC71" {
        value 604;
        description
          "CR5D00D4NC71.";
      }
      enum "CR5D00E4NC7Q" {
        value 605;
        description
          "CR5D00E4NC7Q.";
      }
      enum "CX6DISUFM011" {
        value 606;
        description
          "CX6DISUFM011.";
      }
      enum "ME0DBSUFM071" {
        value 607;
        description
          "ME0DBSUFM071.";
      }
      enum "ME0DBSUFK071" {
        value 608;
        description
          "ME0DBSUFK071.";
      }
      enum "ME0DMSUFM071" {
        value 609;
        description
          "ME0DMSUFM071.";
      }
      enum "ME0D0L4NCB71" {
        value 610;
        description
          "ME0D0L4NCB71.";
      }
      enum "ME0D0LKXFB71" {
        value 611;
        description
          "ME0D0LKXFB71.";
      }
      enum "ME0D0E4NCM71" {
        value 612;
        description
          "ME0D0E4NCM71.";
      }
      enum "ME0D0LMXFA71" {
        value 613;
        description
          "ME0D0LMXFA71.";
      }
      enum "CR5D00LMXF7B" {
        value 614;
        description
          "CR5D00LMXF7B.";
      }
      enum "CR5DE2NLFX7B" {
        value 615;
        description
          "CR5DE2NLFX7B.";
      }
      enum "CR5D00E4NC7B" {
        value 616;
        description
          "CR5D00E4NC7B.";
      }
      enum "CX6D0LEXFA11" {
        value 617;
        description
          "CX6D0LEXFA11.";
      }
      enum "CR5D00E8NC7C" {
        value 618;
        description
          "CR5D00E8NC7C.";
      }
      enum "CR5D00LMXF7C" {
        value 619;
        description
          "CR5D00LMXF7C.";
      }
      enum "CR5DE2NLFX7C" {
        value 620;
        description
          "CR5DE2NLFX7C.";
      }
      enum "CR5D00E4NC7C" {
        value 621;
        description
          "CR5D00E4NC7C.";
      }
      enum "ME0DL2XEFG7E" {
        value 622;
        description
          "ME0DL2XEFG7E.";
      }
      enum "CR5D0L5XFA7E" {
        value 623;
        description
          "CR5D0L5XFA7E.";
      }
      enum "CR5D0L5XFA7F" {
        value 624;
        description
          "CR5D0L5XFA7F.";
      }
      enum "CR5DLAXFAJ7F" {
        value 625;
        description
          "CR5DLAXFAJ7F.";
      }
      enum "ME0D0L5XXE71" {
        value 626;
        description
          "ME0D0L5XXE71.";
      }
      enum "ME0D0LAXXH71" {
        value 627;
        description
          "ME0D0LAXXH71.";
      }
      enum "CR5DL2XFFG7E" {
        value 628;
        description
          "CR5DL2XFFG7E.";
      }
      enum "CR5D0L5XFL70" {
        value 629;
        description
          "CR5D0L5XFL70.";
      }
      enum "CR5DL4XEFG70" {
        value 630;
        description
          "CR5DL4XEFG70.";
      }
      enum "CR5D0EMGFL70" {
        value 631;
        description
          "CR5D0EMGFL70.";
      }
      enum "CR5DL2XEFG71" {
        value 632;
        description
          "CR5DL2XEFG71.";
      }
      enum "CR5D00LFXF76" {
        value 633;
        description
          "CR5D00LFXF76.";
      }
      enum "CR5D00LFXF75" {
        value 634;
        description
          "CR5D00LFXF75.";
      }
      enum "CX6D00LFXF10" {
        value 635;
        description
          "CX6D00LFXF10.";
      }
      enum "ME0D00LFXF70" {
        value 636;
        description
          "ME0D00LFXF70.";
      }
      enum "CR5D00E2NC78" {
        value 637;
        description
          "CR5D00E2NC78.";
      }
      enum "CR5D00E2NC79" {
        value 638;
        description
          "CR5D00E2NC79.";
      }
      enum "CX6D00E2NC10" {
        value 639;
        description
          "CX6D00E2NC10.";
      }
      enum "ME0D00E2NC78" {
        value 640;
        description
          "ME0D00E2NC78.";
      }
      enum "CR5D00E2NF71" {
        value 641;
        description
          "CR5D00E2NF71.";
      }
      enum "CR5D00E2NF72" {
        value 642;
        description
          "CR5D00E2NF72.";
      }
      enum "CX6D00E2NF10" {
        value 643;
        description
          "CX6D00E2NF10.";
      }
      enum "ME0D00E2NF71" {
        value 644;
        description
          "ME0D00E2NF71.";
      }
      enum "CR5D0EFGFL70" {
        value 645;
        description
          "CR5D0EFGFL70.";
      }
      enum "CR5DL5XEFG7L" {
        value 646;
        description
          "CR5DL5XEFG7L.";
      }
      enum "ME0DL2XEFG8E" {
        value 647;
        description
          "ME0DL2XEFG8E.";
      }
      enum "CX6DSFUIM01B" {
        value 648;
        description
          "CX6DSFUIM01B.";
      }
      enum "CX6DSFUIM01C" {
        value 649;
        description
          "CX6DSFUIM01C.";
      }
      enum "CX6D0MPUB510" {
        value 650;
        description
          "CX6D0MPUB510.";
      }
      enum "CX6D0SRUA810" {
        value 651;
        description
          "CX6D0SRUA810.";
      }
      enum "CX6D0MPUD410" {
        value 652;
        description
          "CX6D0MPUD410.";
      }
      enum "ME0DSFUIM07B" {
        value 653;
        description
          "ME0DSFUIM07B.";
      }
      enum "ME0DSFUIM07C" {
        value 654;
        description
          "ME0DSFUIM07C.";
      }
      enum "ME0D0SRUA770" {
        value 655;
        description
          "ME0D0SRUA770.";
      }
      enum "ME0DSFUIA07D" {
        value 656;
        description
          "ME0DSFUIA07D.";
      }
      enum "ME0D00MPUK70" {
        value 657;
        description
          "ME0D00MPUK70.";
      }
      enum "ME0DBSU24071" {
        value 658;
        description
          "ME0DBSU24071.";
      }
      enum "CR57SRU200B" {
        value 659;
        description
          "CR57SRU200B.";
      }
      enum "CR5D0MPUB571" {
        value 660;
        description
          "CR5D0MPUB571.";
      }
      enum "CX6D0MPUB571" {
        value 661;
        description
          "CX6D0MPUB571.";
      }
      enum "TNRD0MPUB571" {
        value 662;
        description
          "TNRD0MPUB571.";
      }
      enum "ME0D0MPUB571" {
        value 663;
        description
          "ME0D0MPUB571.";
      }
      enum "CR5DMPUX8670" {
        value 664;
        description
          "CR5DMPUX8670.";
      }
      enum "CX6DMPUX8670" {
        value 665;
        description
          "CX6DMPUX8670.";
      }
      enum "ME0DMPUX8670" {
        value 666;
        description
          "ME0DMPUX8670.";
      }
      enum "TNRDMPUX8670" {
        value 667;
        description
          "TNRDMPUX8670.";
      }
      enum "CR5D0MPUD471" {
        value 668;
        description
          "CR5D0MPUD471.";
      }
      enum "CX6D0MPUD471" {
        value 669;
        description
          "CX6D0MPUD471.";
      }
      enum "TNRD0MPUD471" {
        value 670;
        description
          "TNRD0MPUD471.";
      }
      enum "CR5D0SRUA871" {
        value 671;
        description
          "CR5D0SRUA871.";
      }
      enum "CX6D0SRUA871" {
        value 672;
        description
          "CX6D0SRUA871.";
      }
      enum "TNRD0SRUA871" {
        value 673;
        description
          "TNRD0SRUA871.";
      }
      enum "ME0D0SRUA871" {
        value 674;
        description
          "ME0D0SRUA871.";
      }
      enum "CR5D0SRUA971" {
        value 675;
        description
          "CR5D0SRUA971.";
      }
      enum "CX6D0SRUA971" {
        value 676;
        description
          "CX6D0SRUA971.";
      }
      enum "TNRD0SRUA971" {
        value 677;
        description
          "TNRD0SRUA971.";
      }
      enum "ME0D0SRUA971" {
        value 678;
        description
          "ME0D0SRUA971.";
      }
      enum "CR5D00E8NB60" {
        value 679;
        description
          "CR5D00E8NB60.";
      }
      enum "ME0D0L8NCA70" {
        value 680;
        description
          "ME0D0L8NCA70.";
      }
      enum "ME0D0L4NCB70" {
        value 681;
        description
          "ME0D0L4NCB70.";
      }
      enum "ME0D0L2NCB70" {
        value 682;
        description
          "ME0D0L2NCB70.";
      }
      enum "ME0D0LFXFA70" {
        value 683;
        description
          "ME0D0LFXFA70.";
      }
      enum "ME0D0LMXFA70" {
        value 684;
        description
          "ME0D0LMXFA70.";
      }
      enum "ME0D0E4NCM70" {
        value 685;
        description
          "ME0D0E4NCM70.";
      }
      enum "ME0D0LKXFB70" {
        value 686;
        description
          "ME0D0LKXFB70.";
      }
      enum "ME0DE2NLEX7B" {
        value 687;
        description
          "ME0DE2NLEX7B.";
      }
      enum "ME0DL3XEFG7B" {
        value 688;
        description
          "ME0DL3XEFG7B.";
      }
      enum "ME0D0LEXFB71" {
        value 689;
        description
          "ME0D0LEXFB71.";
      }
      enum "ME0D0LAXFA70" {
        value 690;
        description
          "ME0D0LAXFA70.";
      }
      enum "ME0D0LEXFB70" {
        value 691;
        description
          "ME0D0LEXFB70.";
      }
      enum "ME0D0E2NCB70" {
        value 692;
        description
          "ME0D0E2NCB70.";
      }
      enum "ME0D0EMGFB70" {
        value 693;
        description
          "ME0D0EMGFB70.";
      }
      enum "ME0D0LAXXB70" {
        value 694;
        description
          "ME0D0LAXXB70.";
      }
      enum "ME0D0L5XXB70" {
        value 695;
        description
          "ME0D0L5XXB70.";
      }
      enum "CR5DLPUFE07E" {
        value 696;
        description
          "CR5DLPUFE07E.";
      }
      enum "ME0DBSUFB070" {
        value 697;
        description
          "ME0DBSUFB070.";
      }
      enum "ME0DBSUFC870" {
        value 698;
        description
          "ME0DBSUFC870.";
      }
      enum "ME0DBSUFK070" {
        value 699;
        description
          "ME0DBSUFK070.";
      }
      enum "CR5DLPUFK070" {
        value 700;
        description
          "CR5DLPUFK070.";
      }
      enum "CR9DLPUFK080" {
        value 701;
        description
          "CR9DLPUFK080.";
      }
      enum "CR9D00EDNB8L" {
        value 702;
        description
          "CR9D00EDNB8L.";
      }
      enum "CR9D00EDNB8P" {
        value 703;
        description
          "CR9D00EDNB8P.";
      }
      enum "CX6D00EPXFA0" {
        value 704;
        description
          "CX6D00EPXFA0.";
      }
      enum "CR9D00EKNB80" {
        value 705;
        description
          "CR9D00EKNB80.";
      }
      enum "CR9DLPUFT280" {
        value 706;
        description
          "CR9DLPUFT280.";
      }
      enum "CR9D00DDNC80" {
        value 707;
        description
          "CR9D00DDNC80.";
      }
      enum "CR9D00DDNC8P" {
        value 708;
        description
          "CR9D00DDNC8P.";
      }
      enum "CR9D00EENB80" {
        value 709;
        description
          "CR9D00EENB80.";
      }
      enum "CR9D00EENB8P" {
        value 710;
        description
          "CR9D00EENB8P.";
      }
      enum "CR9D00DDNC8L" {
        value 711;
        description
          "CR9D00DDNC8L.";
      }
      enum "CR9D00EENB8L" {
        value 712;
        description
          "CR9D00EENB8L.";
      }
      enum "CR9D00EKNB8P" {
        value 713;
        description
          "CR9D00EKNB8P.";
      }
      enum "CR9D00EKNB8L" {
        value 714;
        description
          "CR9D00EKNB8L.";
      }
      enum "CR9D00E8KC80" {
        value 715;
        description
          "CR9D00E8KC80.";
      }
      enum "CR9D00E8KC8P" {
        value 716;
        description
          "CR9D00E8KC8P.";
      }
      enum "CR9DE8KE8N8R" {
        value 717;
        description
          "CR9DE8KE8N8R.";
      }
      enum "CR9D00EKNB8M" {
        value 718;
        description
          "CR9D00EKNB8M.";
      }
      enum "CX6D00EKNBA1" {
        value 719;
        description
          "CX6D00EKNBA1.";
      }
      enum "CX6D00EKNBA0" {
        value 720;
        description
          "CX6D00EKNBA0.";
      }
      enum "CX6D00DDNCA0" {
        value 721;
        description
          "CX6D00DDNCA0.";
      }
      enum "CX6D00EENBA0" {
        value 722;
        description
          "CX6D00EENBA0.";
      }
      enum "CX6D60T220A0" {
        value 723;
        description
          "CX6D60T220A0.";
      }
      enum "CR9D00EENB83" {
        value 724;
        description
          "CR9D00EENB83.";
      }
      enum "CR9D00E8NC8P" {
        value 725;
        description
          "CR9D00E8NC8P.";
      }
      enum "CR9D00D8NC8P" {
        value 726;
        description
          "CR9D00D8NC8P.";
      }
      enum "CR9D00EPXF8P" {
        value 727;
        description
          "CR9D00EPXF8P.";
      }
      enum "CR5D00LKXF6P" {
        value 728;
        description
          "CR5D00LKXF6P.";
      }
      enum "CR5D00EDNB6P" {
        value 729;
        description
          "CR5D00EDNB6P.";
      }
      enum "CR5D00EDNB61" {
        value 730;
        description
          "CR5D00EDNB61.";
      }
      enum "ME0D0L5XXE70" {
        value 731;
        description
          "ME0D0L5XXE70.";
      }
     enum "ME0D0L5XXM70" {
        value 732;
        description
          "ME0D0L5XXM70.";
      }  
       enum "CR5D00LMXF7P" {
        value 733;
        description
          "CR5D00LMXF7P.";
      }
     enum "CR5DE2NLFX7P" {
        value 734;
        description
          "CR5DE2NLFX7P.";
      }          
     enum "CR5D0MPUB760" {
        value 735;
        description
          "CR5D0MPUB760.";
      }
     enum "CR9D00MPUS80" {
        value 736;
        description
          "CR9D00MPUS80.";
      }
      enum "CR9D00EPXF81" {
        value 737;
        description
          "CR9D00EPXF81.";
      }
      enum "CR9D000CMU61" {
        value 738;
        description
          "CR9D000CMU61.";
      }
      enum "CR9D000CMU62" {
        value 739;
        description
          "CR9D000CMU62.";
      }
      enum "CR5D0MPUN160" {
        value 740;
        description
          "CR5D0MPUN160.";
      }
      enum "CR5DSFUIT260" {
        value 741;
        description
          "CR5DSFUIT260.";
      }
      enum "CR9DLPUFK081" {
        value 742;
        description
          "CR9DLPUFK081.";
      }
      enum "CR9D00EPXF8L" {
        value 743;
        description
          "CR9D00EPXF8L.";
      }
      enum "CR5D0MPUB772" {
        value 744;
        description
          "CR5D0MPUB772.";
      }
      enum "CX6D0MPUB772" {
        value 745;
        description
          "CX6D0MPUB772.";
      }
      enum "TNRD0MPUB770" {
        value 746;
        description
          "TNRD0MPUB770.";
      }
      enum "CX6D0MPUB710" {
        value 747;
        description
          "CX6D0MPUB710.";
      }
      enum "ME0D0MPUB770" {
        value 748;
        description
          "ME0D0MPUB770.";
      }
      enum "CR5DSFUGK070" {
        value 749;
        description
          "CR5DSFUGK070.";
      }
      enum "CX6DSFUGK070" {
        value 750;
        description
          "CX6DSFUGK070.";
      }
      enum "TNRDSFUGK070" {
        value 751;
        description
          "TNRDSFUGK070.";
      }
      enum "CX6DSFUIG010" {
        value 752;
        description
          "CX6DSFUIG010.";
      }
      enum "ME0DSFUGK070" {
        value 753;
        description
          "ME0DSFUGK070.";
      } 
     enum "CR9DLPUFT281" {
        value 754;
        description
          "CR9DLPUFT281.";
      }                    
     enum "CX6DSFUIT01B" {
        value 755;
        description
          "CX6DSFUIT01B.";
      }
     enum "CX6D0SRUA910" {
        value 756;
        description
          "CX6D0SRUA910.";
      }
     enum "CX6DSFUIT01C" {
        value 757;
        description
          "CX6DSFUIT01C.";
      }      
      enum "CR5D0SRUAB73" {
        value 758;
        description
          "CR5D0SRUAB73.";
      }
      enum "ME0D0SRUAB70" {
        value 759;
        description
          "ME0D0SRUAB70.";
      }
      enum "CR5D0SRUAC7A" {
        value 760;
        description
          "CR5D0SRUAC7A.";
      }
      enum "CX6D0SRUAC7A" {
        value 761;
        description
          "CX6D0SRUAC7A.";
      }
      enum "TNRD0SRUAC70" {
        value 762;
        description
          "TNRD0SRUAC70.";
      }
      enum "CX6D0SRUAC10" {
        value 763;
        description
          "CX6D0SRUAC10.";
      }
      enum "ME0D0SRUAC7A" {
        value 764;
        description
          "ME0D0SRUAC7A.";
      }
      enum "CR5D0SRUAC70" {
        value 765;
        description
          "CR5D0SRUAC70.";
      }
      enum "CR5D0MPUB870" {
        value 766;
        description
          "CR5D0MPUB870.";
      }
      enum "CR5DSFUFK070" {
        value 767;
        description
          "CR5DSFUFK070.";
      }
      enum "CX6D0SFUF870" {
        value 768;
        description
          "CX6D0SFUF870.";
      }
      enum "TNRDSFUFK070" {
        value 769;
        description
          "TNRDSFUFK070.";
      }
      enum "CX6DSFUIF070" {
        value 770;
        description
          "CX6DSFUIF070.";
      }
      enum "ME0DSFUIF070" {
        value 771;
        description
          "ME0DSFUIF070.";
      }
      enum "CR5DLPUFT261" {
        value 772;
        description
          "CR5DLPUFT261.";
      }
      enum "CR5DLPUFT264" {
        value 773;
        description
          "CR5DLPUFT264.";
      }
      enum "CR5DSFUIT250" {
        value 774;
        description
          "CR5DSFUIT250.";
      }
      enum "CR5DSFUIT26H" {
        value 775;
        description
          "CR5DSFUIT26H.";
      }
      enum "CR5DLPUFF170" {
        value 776;
        description
          "CR5DLPUFF170.";
      }
      enum "CR5DLPUF5270" {
        value 777;
        description
          "CR5DLPUF5270.";
      }
      enum "CR5DLPUFF17R" {
        value 778;
        description
          "CR5DLPUFF17R.";
      }
      enum "CR5DEKBEBX7B" {
        value 779;
        description
          "CR5DEKBEBX7B.";
      }
      enum "CX6DISUFF110" {
        value 780;
        description
          "CX6DISUFF110.";
      }
      enum "CX6DISUFF11R" {
        value 781;
        description
          "CX6DISUFF11R.";
      }
      enum "CX6DF1E2NC10" {
        value 782;
        description
          "CX6DF1E2NC10.";
      }
      enum "CX6DF1E2NB10" {
        value 783;
        description
          "CX6DF1E2NB10.";
      }
      enum "CX6DF1EFXC10" {
        value 784;
        description
          "CX6DF1EFXC10.";
      }
      enum "CX6DE1KEBX10" {
        value 785;
        description
          "CX6DE1KEBX10.";
      }
      enum "CX6DEKBEBX10" {
        value 786;
        description
          "CX6DEKBEBX10.";
      }
      enum "CX6DF1E2NC1B" {
        value 787;
        description
          "CX6DF1E2NC1B.";
      }
      enum "CX6DF1E2NB1B" {
        value 788;
        description
          "CX6DF1E2NB1B.";
      }
      enum "CX6DF1EFXC1B" {
        value 789;
        description
          "CX6DF1EFXC1B.";
      }
      enum "CX6DE1KEBX1B" {
        value 790;
        description
          "CX6DE1KEBX1B.";
      }
      enum "CX6DEKBEBX1B" {
        value 791;
        description
          "CX6DEKBEBX1B.";
      }
      enum "CR5DF1EFXC7P" {
        value 792;
        description
          "CR5DF1EFXC7P.";
      }
      enum "CR5DLPUFF273" {
        value 793;
        description
          "CR5DLPUFF273.";
      }
      enum "CR5DLPUFF272" {
        value 794;
        description
          "CR5DLPUFF272.";
      }
      enum "CR5DLPUFD07E" {
        value 795;
        description
          "CR5DLPUFD07E.";
      }
      enum "ME0D0LFXFB70" {
        value 796;
        description
          "ME0D0LFXFB70.";
      }
      enum "ANND00CXPA00" {
        value 797;
        description
          "ANND00CXPA00.";
      }
      enum "ANND000PIU00" {
        value 798;
        description
          "ANND000PIU00.";
      }
      enum "ANND000PIU01" {
        value 799;
        description
          "ANND000PIU01.";
      }
      enum "ANND000FAN00" {
         value 800;
        description
           "ANND000FAN00.";
       } 
      enum "CX6DISUFF210" {
        value 801;
        description
          "CX6DISUFF210.";
      }
      enum "ME0DBSUFM072" {
        value 802;
        description
          "ME0DBSUFM072.";
      }
      enum "CR5DSPUIM070" {
        value 803;
        description
          "CR5DSPUIM070.";
      }
      enum "CR5DF1E2NC70" {
        value 804;
        description
          "CR5DF1E2NC70.";
      }
      enum "CR5DF1E2NB70" {
        value 805;
        description
          "CR5DF1E2NB70.";
      }
      enum "CR5DF1EFXC70" {
        value 806;
        description
          "CR5DF1EFXC70.";
      }
      enum "CR5DE1KEBX70" {
        value 807;
        description
          "CR5DE1KEBX70.";
      }
      enum "CR5DEKBEBX70" {
        value 808;
        description
          "CR5DEKBEBX70.";
      }
      enum "CR5DF1E2NC7B" {
        value 809;
        description
          "CR5DF1E2NC7B.";
      }
      enum "CR5DF1E2NB7B" {
        value 810;
        description
          "CR5DF1E2NB7B.";
      }
      enum "CR5DF1EFXC7B" {
        value 811;
        description
          "CR5DF1EFXC7B.";
      }
      enum "CR5DE1KEBX7B" {
        value 812;
        description
          "CR5DE1KEBX7B.";
      }
     enum "CX6DISUFM012" {
        value 813;
        description
          "CX6DISUFM012.";
      }
     enum "CX6D00E8NC70" {
        value 814;
        description
          "CX6D00E8NC70.";
      }
      enum "FAN-F1A-14H24Q" {
        value 815;
        description
          "FAN-F1A-14H24Q.";
      }
      enum "CR9D0MPUN180-VMPU" {
        value 816;
        description
          "CR9D0MPUN180-VMPU.";
      }
      enum "CR9D0MPUP180-VMPU" {
        value 817;
        description
          "CR9D0MPUP180-VMPU.";
      }
      enum "CR5D00LRXF60" {
        value 818;
        description
          "CR5D00LRXF60.";   
      }
      enum "CR5D00EDNB62" {
        value 819;
        description
          "CR5D00EDNB62.";   
      }
      enum "CR5D00E4KC60" {
        value 820;
        description
          "CR5D00E4KC60.";   
      }
      enum "CR5D00LMXF62" {
        value 821;
        description
          "CR5D00LMXF62.";   
      }
      enum "CR5D00E8NB62" {
        value 822;
        description
          "CR5D00E8NB62.";   
      }
      enum "CR5DLPUFT070" {
        value 823;
        description
          "CR5DLPUFT070.";
      }
      enum "CX6D0MPUB810" {
        value 824;
        description
          "CX6D0MPUB810.";
      }
      enum "CX6DSFUIT27C" {
        value 825;
        description
          "CX6DSFUIT27C.";
      }
      enum "CX6D0SRUAG10" {
        value 826;
        description
          "CX6D0SRUAG10.";
      }
      enum "CX6DSFUIU01F" {
        value 827;
        description
          "CX6DSFUIU01F.";
      }
      enum "ME0DBSUFT070" {
        value 828;
        description
          "ME0DBSUFT070.";
      }
      enum "ME0DMSUFT070" {
        value 829;
        description
          "ME0DMSUFT070.";
      }      
      enum "CR5D00E8NB70" {
        value 830;
        description
          "CR5D00E8NB70.";
      }
      enum "CR5DEDVE8N7P" {
        value 831;
        description
          "CR5DEDVE8N7P.";
      }
      enum "CR5D00EIYB7P" {
        value 832;
        description
          "CR5D00EIYB7P.";
      }
      enum "CR5D00EENB7Q" {
        value 833;
        description
          "CR5D00EENB7Q.";
      }
      enum "CX6DISUFT010" {
        value 834;
        description
           "CX6DISUFT010.";
      }
      enum "CR5D00EENB73" {
        value 835;
        description
          "CR5D00EENB73.";
      }
        enum "CX6DLPUFK0A0" {
        value 836;
        description
          "CX6DLPUFK0A0.";   
      }    
      enum "ME0DL2XEFG7B" {
        value 837;
        description
          "ME0DL2XEFG7B.";
      }
      enum "ME0DL4XEBG7B" {
        value 838;
        description
          "ME0DL4XEBG7B.";
      }
      enum "CR5D0LBXFA71" {
        value 839;
        description
          "CR5D0LBXFA71.";
      }
      enum "ME0D0MPUB771" {
        value 840;
        description
          "ME0D0MPUB771.";
      }
      enum "CR5D0MPUB773" {
        value 841;
        description
          "CR5D0MPUB773.";
      }
      enum "CR5D0SRUAC7B" {
        value 842;
        description
          "CR5D0SRUAC7B.";
      }
      enum "ME0D0SRUAC7B" {
        value 843;
        description
          "ME0D0SRUAC7B.";
      }
      enum "CR5D0SRUAC71" {
        value 844;
        description
          "CR5D0SRUAC71.";
      }
      enum "CR5D0MPUB871" {
        value 845;
        description
          "CR5D0MPUB871.";
      }
      enum "CX6D0MPUB871" {
        value 846;
        description
          "CX6D0MPUB871.";
      }
      enum "CX6D0SRUAC71" {
        value 847;
        description
          "CX6D0SRUAC71.";
      }
      enum "TNRD0MPUB871" {
        value 848;
        description
          "TNRD0MPUB871.";
      }
      enum "TNRD0SRUAC71" {
        value 849;
        description
          "TNRD0SRUAC71.";
      }
      enum "CR5DMPUX8671" {
        value 850;
        description
          "CR5DMPUX8671.";
      }
      enum "ME0DMPUX8671" {
        value 851;
        description
          "ME0DMPUX8671.";
      }
      enum "CR5DEDVE8N70" {
        value 852;
        description
          "CR5DEDVE8N70.";
      }
      enum "CR5D00EENB72" {
        value 853;
        description
          "CR5D00EENB72.";
      }
      enum "CR8B0BKP03C0" {
        value 854;
        description
          "CR8B0BKP03C0.";
      }
      enum "CR8B0BKP03C1" {
        value 855;
        description
          "CR8B0BKP03C1.";
      }
      enum "CR8B0BKP03C2" {
        value 856;
        description
          "CR8B0BKP03C2.";
      }
      enum "CR8B0BKP03C3" {
        value 857;
        description
          "CR8B0BKP03C3.";
      }
      enum "CR8D0IPU2TC1" {
        value 858;
        description
          "CR8D0IPU2TC1.";
      }
      enum "CR8D0IPU2TC2" {
        value 859;
        description
          "CR8D0IPU2TC2.";
      }
      enum "CR8DIPU1T2C3" {
        value 860;
        description
          "CR8DIPU1T2C3.";
      }
      enum "CR8DIPU1T2C4" {
        value 861;
        description
          "CR8DIPU1T2C4.";
      }
      enum "CR5D0IPU2TC1" {
        value 862;
        description
          "CR5D0IPU2TC1.";
      }
      enum "CR5D0IPU2TC2" {
        value 863;
        description
          "CR5D0IPU2TC2.";
      }
      enum "CR5DIPU1T2C3" {
        value 864;
        description
          "CR5DIPU1T2C3.";
      }
      enum "CR5DIPU1T2C4" {
        value 865;
        description
          "CR5DIPU1T2C4.";
      }
      enum "TNRD0IPU2TC1" {
        value 866;
        description
          "TNRD0IPU2TC1.";
      }
      enum "TNRDIPU1T2C3" {
        value 867;
        description
          "TNRDIPU1T2C3.";
      }
      enum "CR5DLPUFT071" {
        value 868;
        description
          "CR5DLPUFT071.";
      }
      enum "CR5DLPUFT072" {
        value 869;
        description
          "CR5DLPUFT072.";
      }
      enum "CX6DISUFT011" {
        value 870;
        description
          "CX6DISUFT011.";
      }
      enum "CR8DIPU1T2C1" {
        value 871;
        description
          "CR8DIPU1T2C1.";
      }
      enum "CR8DIPU1T2C2" {
        value 872;
        description
          "CR8DIPU1T2C2.";
      }
      enum "CR8DIPU480C1" {
        value 873;
        description
          "CR8DIPU480C1.";
      }
      enum "CR8DIPU480C2" {
        value 874;
        description
          "CR8DIPU480C2.";
      }
      enum "TNRDIPU1T2C1" {
        value 875;
        description
          "TNRDIPU1T2C1.";
      }
      enum "TNRDIPU480C1" {
        value 876;
        description
          "TNRDIPU480C1.";
      }
      enum "ME0DBSUFT072" {
        value 877;
        description
          "ME0DBSUFT072.";
    }
      enum "ME0DMSUFT073" {
        value 878;
    description
          "ME0DMSUFT073.";
      }
      enum "ME0DBSUFT074" {
        value 879;
        description
          "ME0DBSUFT074.";
      }
      enum "ME0DMSUFT075" {
        value 880;
        description
          "ME0DMSUFT075.";
      }
      	enum "CR5D00E4KB60" {
        value 881;
        description
          "CR5D00E4KB60.";
    }
	enum "CR5D00NDNC60" {
        value 882;
        description
          "CR5D00NDNC60.";
    }
	enum "CR5D00LRXF61" {
        value 883;
        description
          "CR5D00LRXF61.";
    }
	enum "CR5D00EDNB63" {
        value 884;
        description
          "CR5D00EDNB63.";
    }
	enum "CR5D00E4KB61" {
        value 885;
        description
          "CR5D00E4KB61.";
    }
	enum "CR5D00NDNC61" {
        value 886;
        description
          "CR5D00NDNC61.";
    }
    enum "CR9D00EPYF8P" {
        value 887;
        description
          "CR9D00EPYF8P.";
    }
	enum "CR5D0MPUQ1D1" {
        value 888;
        description
          "CR5D0MPUQ1D1.";
    }
	enum "CR5D0MPUQ1D0" {
        value 889;
        description
          "CR5D0MPUQ1D0.";
    }
	enum "CR9D0MPUQ180" {
        value 890;
        description
          "CR9D0MPUQ180.";
    }
	enum "CR9D0MPUR180" {
        value 891;
        description
          "CR9D0MPUR180.";
    }
	enum "CR5D0SFUT2D1" {
        value 892;
        description
          "CR5D0SFUT2D1.";
    }
	enum "CR5D0SFUT2D2" {
        value 893;
        description
          "CR5D0SFUT2D2.";
    }
	enum "CR5D00EENBD0" {
        value 894;
        description
          "CR5D00EENBD0.";
    }
	enum "CR5D00EENBD1" {
        value 895;
        description
          "CR5D00EENBD1.";
    }
	enum "CR5D00EPXFD1" {
        value 896;
        description
          "CR5D00EPXFD1.";
    }
	enum "CR5D00EPXFD0" {
        value 897;
        description
          "CR5D00EPXFD0.";
    }
      enum "CR5D0MPUB661" {
        value 898;
        description
          "CR5D0MPUB661.";
      }
      enum "CR5D0MPUA850" {
        value 899;
        description
          "CR5D0MPUA850.";
      }
      enum "CR5D0MPUA851" {
        value 900;
        description
          "CR5D0MPUA851.";
      }
    enum "CR5DVSUIK071" {
        value 901;
        description
          "CR5DVSUIK071.";
    }
    enum "CR5DVSUIK073" {
        value 902;
        description
          "CR5DVSUIK073.";
    }
    enum "ME0DVSUIK071" {
        value 903;
        description
          "ME0DVSUIK071.";
    }
    enum "ME0DVSUIK073" {
        value 904;
        description
          "ME0DVSUIK073.";
    }
    enum "CR5DVSUIK070" {
        value 905;
        description
          "CR5DVSUIK070.";
    }
    enum "CR5DVSUIK072" {
        value 906;
        description
          "CR5DVSUIK072.";
    }
    enum "CR5DJYSUK072" {
        value 907;
        description
          "CR5DJYSUK072.";
    }
    enum "ME0DVSUIK070" {
        value 908;
        description
          "ME0DVSUIK070.";
    }
    enum "ME0DVSUIK072" {
        value 909;
        description
          "ME0DVSUIK072.";
    }
    enum "ME0DJYSUK070" {
        value 910;
        description
          "ME0DJYSUK070.";
    }
    enum "CR8DSFUI4TC1" {
        value 911;
        description
          "CR8DSFUI4TC1.";
    }
    enum "CR8DSFUI4TC3" {
        value 912;
        description
          "CR8DSFUI4TC3.";
    }
    enum "CR8DSFUI4TC0" {
        value 913;
        description
          "CR8DSFUI4TC0.";
    }
    enum "CR8DSFUI4TC2" {
        value 914;
        description
          "CR8DSFUI4TC2.";
    }
    enum "CR8D00EKNBCP" {
        value 915;
        description
          "CR8D00EKNBCP.";
    }
    enum "CR8D00EKNBCR" {
        value 916;
        description
          "CR8D00EKNBCR.";
    }
    enum "CR8D00EKNBCQ" {
        value 917;
        description
          "CR8D00EKNBCQ.";
    }
    enum "CR8D00EKNBC0" {
        value 918;
        description
          "CR8D00EKNBC0.";
    }
    enum "CR8D00LRXFCP" {
        value 919;
        description
          "CR8D00LRXFCP.";
    }
    enum "CR8D00LRXFCR" {
        value 920;
        description
          "CR8D00LRXFCR.";
    }
    enum "CR8D00LRXFCQ" {
        value 921;
        description
          "CR8D00LRXFCQ.";
    }
    enum "CR8D00LRXFC0" {
        value 922;
        description
          "CR8D00LRXFC0.";
    }
    enum "CR5DSFUIT27M" {
        value 923;
        description
          "CR5DSFUIT27M.";
          }
    enum "CR5DSFUIT27N" {
        value 924;
        description
          "CR5DSFUIT27N.";
          }
    enum "CR5DSFUIT27K" {
        value 925;
        description
          "CR5DSFUIT27K.";
          }
    enum "CR5DSFUIT27L" {
        value 926;
        description
          "CR5DSFUIT27L.";
          }
    enum "CX6DSFUIT27F" {
        value 927;
        description
          "CX6DSFUIT27F.";
          }
    enum "CX6DSFUIU07G" {
        value 928;
        description
          "CX6DSFUIU07G.";
          }
    enum "TNRDSFUIT27G" {
        value 929;
        description
          "TNRDSFUIT27G.";
          }
    enum "TNRDSFUIU07H" {
        value 930;
        description
          "TNRDSFUIU07H.";
          }
    enum "ME0DSFUIT07E" {
        value 931;
        description
          "ME0DSFUIT07E.";
          }
    enum "ME0DSFUIT17E" {
        value 932;
        description
          "ME0DSFUIT17E.";
          }
    enum "ME0DSFUIT07F" {
        value 933;
        description
          "ME0DSFUIT07F.";
          }
    enum "ME0DSFUIT17F" {
        value 934;
        description
          "ME0DSFUIT17F.";
          }
    enum "CR5D0MPUB970" {
        value 935;
        description
          "CR5D0MPUB970.";
          }
    enum "CR5D0MPUB971" {
        value 936;
        description
          "CR5D0MPUB971.";
          }
    enum "CX6D0MPUB970" {
        value 937;
        description
          "CX6D0MPUB970.";
          }
    enum "CX6D0MPUB910" {
        value 938;
        description
          "CX6D0MPUB910.";
          }
    enum "ME0DMPUX8970" {
        value 939;
        description
          "ME0DMPUX8970.";
          }
    enum "ME0DMPUX8971" {
        value 940;
        description
          "ME0DMPUX8971.";
          }
    enum "TNRD0MPUB970" {
        value 941;
        description
          "TNRD0MPUB970.";
          }
    enum "CR5D0SRUAD70" {
        value 942;
        description
          "CR5D0SRUAD70.";
          }
    enum "CR5D0SRUAD71" {
        value 943;
        description
          "CR5D0SRUAD71.";
          }
    enum "CX6D0SRUAD70" {
        value 944;
        description
          "CX6D0SRUAD70.";
          }
    enum "TNRD0SRUAD70" {
        value 945;
        description
          "TNRD0SRUAD70.";
          }
    enum "CR5D0SRUAE70" {
        value 946;
        description
          "CR5D0SRUAE70.";
          }
    enum "CR5D0SRUAE71" {
        value 947;
        description
          "CR5D0SRUAE71.";
          }
    enum "CX6D0SRUAE70" {
        value 948;
        description
          "CX6D0SRUAE70.";
          }
    enum "CX6D0SRUAE10" {
        value 949;
        description
          "CX6D0SRUAE10.";
          }
    enum "ME0D0SRUAD71" {
        value 950;
        description
          "ME0D0SRUAD71.";
          }
    enum "ME0D0SRUAD70" {
        value 951;
        description
          "ME0D0SRUAD70.";
          }
    enum "TNRD0SRUAE70" {
        value 952;
        description
          "TNRD0SRUAE70.";
          }
    enum "CR8D0MPUA1C0" {
        value 953;
        description
          "CR8D0MPUA1C0.";
    }
    enum "CR8D0MPUA1C1" {
        value 954;
        description
          "CR8D0MPUA1C1.";
    }
    enum "CR5D00ICUC51" {
        value 955;
        description
          "CR5D00ICUC51.";
    }
    enum "CR5D00ICUC52" {
        value 956;
        description
          "CR5D00ICUC52.";
    }
    enum "ANRD00CXPA00" {
        value 968;
        description
          "ANRD00CXPA00.";
    }
    enum "ANRD00CXPA01" {
        value 969;
        description
          "ANRD00CXPA01.";
    }
    enum "ANRD01CXPA00" {
        value 970;
        description
          "ANRD01CXPA00.";
    }
    enum "ANRD01CXPB00" {
        value 971;
        description
          "ANRD01CXPB00.";
    }
    enum "CR8DCXP160C0" {
        value 972;
        description
          "CR8DCXP160C0.";
    }
    enum "CR8DCXP160C1" {
        value 973;
        description
          "CR8DCXP160C1.";
    }
    enum "CR8DCXP160C2" {
        value 974;
        description
          "CR8DCXP160C2.";
    }
    enum "CR8DCXP160C3" {
        value 975;
        description
          "CR8DCXP160C3.";
    }
    enum "CR5D00EDNB64" {
        value 976;
        description
          "CR5D00EDNB64.";
    }
    enum "CR9P9KHALM8B" {
        value 977;
        description
          "CR9P9KHALM8B.";
    }
    enum "CR8DIPU240C1" {
        value 978;
        description
          "CR8DIPU240C1.";
    }
    enum "CR8DIPU240C2" {
        value 979;
        description
          "CR8DIPU240C2.";
    }
      enum "CR9D0MPUR181" {
        value 986;
        description
          "CR9D0MPUR181.";
      }
    enum "CR9D0SFUT48G" {
        value 987;
        description
          "CR9D0SFUT48G.";
      }	
    enum "CR5D00E4KB62" {
        value 988;
        description
          "CR5D00E4KB62.";
    }
    enum "CR5D00LRXF62" {
        value 989;
        description
          "CR5D00LRXF62.";
    }
    enum "CR5DSFUIT076" {
        value 995;
        description
          "CR5DSFUIT076.";
    }
    enum "CR5DSFUIT077" {
        value 996;
        description
          "CR5DSFUIT077.";
    }
    enum "CX6DSFUIT072" {
        value 997;
        description
          "CX6DSFUIT072.";
    }
    enum "TNRDSFUIT072" {
        value 998;
        description
          "TNRDSFUIT072.";
    }
    enum "CX6DSFUIT27J" {
        value 999;
        description
          "CX6DSFUIT27J.";
    }
    enum "CR5DSFUIT078" {
        value 1000;
        description
          "CR5DSFUIT078.";
    }
    enum "CR5DSFUIT079" {
        value 1001;
        description
          "CR5DSFUIT079.";
    }
    enum "CX6DSFUIT073" {
        value 1002;
        description
          "CX6DSFUIT073.";
    }
    enum "TNRDSFUIT073" {
        value 1003;
        description
          "TNRDSFUIT073.";
    }
    enum "CX6DSFUIT21H" {
        value 1004;
        description
          "CX6DSFUIT21H.";
    }
    enum "CR5D0SRUAC76" {
      value 1011;
      description
        "CR5D0SRUAC76.";
    }
    }
    description
      "Hardware-board-type.";
  }
  
  typedef hardware-hard-type {
    type enumeration {
      enum "unknown" {
        value 1;
        description
          "Not Equipped.";
      }
      enum "ATN905" {
        value 2;
        description
          "ATN905 chassis.";
      }
      enum "ATN910C-E" {
        value 3;
        description
          "ATN910C-E chassis.";
      }
      enum "ANGMHSTE0110" {
        value 4;
        description
          "ANGMHSTE0110.";
      }
      enum "ETN500-F" {
        value 5;
        description
          "ETN500-F chassis.";
      }
      enum "NE05E-SR" {
        value 6;
        description
          "NE05E-SR chassis.";
      }
      enum "CR5B0BKP0383" {
        value 7;
        description
          "CR5B0BKP0383.";
      }
      enum "CR5B0BKP0382" {
        value 8;
        description
          "CR5B0BKP0382.";
      }
      enum "NE08E-S9" {
        value 9;
        description
          "NE08E-S9 chassis.";
      }
      enum "ANPM001AICF0" {
        value 10;
        description
          "ANPM001AICF0.";
      }
      enum "ANPM001DICF0" {
        value 11;
        description
          "ANPM001DICF0.";
      }
      enum "LNPM001AICF0" {
        value 12;
        description
          "LNPM001AICF0.";
      }
      enum "ANDD03CXPA00" {
        value 13;
        description
          "ANDD03CXPA00.";
      }
      enum "ANKD00CXPB02" {
        value 14;
        description
          "ANKD00CXPB02.";
      }
      enum "NEDD00CXPB00" {
        value 15;
        description
          "NEDD00CXPB00.";
      }
      enum "NECM000AIC01" {
        value 16;
        description
          "NECM000AIC01.";
      }
      enum "NEJD00CXPA00" {
        value 17;
        description
          "NEJD00CXPA00.";
      }
      enum "CR5D00EJXF60" {
        value 18;
        description
          "CR5D00EJXF60.";
      }
      enum "ATN950C" {
        value 19;
        description
          "ATN 950C chassis.";
      }
      enum "ATN910C-A" {
        value 20;
        description
          "ATN 910C-A chassis.";
      }
      enum "ATN910C-B" {
        value 21;
        description
          "ATN 910C-B chassis.";
      }
      enum "ATN910C-D" {
        value 22;
        description
          "ATN910C-D.";
      }
      enum "ANKD00CXPA00" {
        value 23;
        description
          "ANKD00CXPA00.";
      }
      enum "ANK200CXPA00" {
        value 24;
        description
          "ANK200CXPA00.";
      }
      enum "ANKD00CXPB00" {
        value 25;
        description
          "ANKD00CXPB00.";
      }
      enum "ANGMHSTA0111" {
        value 26;
        description
          "ANGMHSTA0111.";
      }
      enum "ANGMHSTA0211" {
        value 27;
        description
          "ANGMHSTA0211.";
      }
      enum "ANGMHSTB0111" {
        value 28;
        description
          "ANGMHSTB0111.";
      }
      enum "ANGMHSTB0211" {
        value 29;
        description
          "ANGMHSTB0211.";
      }
      enum "ANGMHSTD0100" {
        value 30;
        description
          "ANGMHSTD0100.";
      }
      enum "ANGMHSTD0200" {
        value 31;
        description
          "ANGMHSTD0200.";
      }
      enum "ANGMHSTF0110" {
        value 32;
        description
          "ANGMHSTF0110.";
      }
      enum "ANGMHSTA0311" {
        value 33;
        description
          "ANGMHSTA0311.";
      }
      enum "ANGMHSTB0311" {
        value 34;
        description
          "ANGMHSTB0311.";
      }
      enum "ANGMHSTD0311" {
        value 35;
        description
          "ANGMHSTD0311.";
      }
      enum "ATN980B-DC" {
        value 36;
        description
          "ATN 980B-DC chassis.";
      }
      enum "ATN980C" {
        value 37;
        description
          "ATN 980C chassis.";
      }
      enum "ATN980B-AC-A" {
        value 38;
        description
          "ATN 980B-AC-A chassis.";
      }
      enum "ATN980B-AC-C" {
        value 39;
        description
          "ATN 980B-AC-C chassis.";
      }
      enum "ATN980B-AC-B" {
        value 40;
        description
          "ATN 980B-AC-B chassis.";
      }
      enum "ANJ1CXP" {
        value 41;
        description
          "ANJ1CXP.";
      }
      enum "TNF5PIU" {
        value 42;
        description
          "TNF5PIU.";
      }
      enum "TPJ1PIU" {
        value 43;
        description
          "ANJ1PIU.";
      }
      enum "ANKD000PIU00" {
        value 44;
        description
          "ANKD000PIU00.";
      }
      enum "ANGD00APIU00" {
        value 45;
        description
          "ANGD00APIU00.";
      }
      enum "ES5M0PSD1700" {
        value 46;
        description
          "ES5M0PSD1700.";
      }
      enum "TNF5APIU" {
        value 47;
        description
          "ANJ1APIU.";
      }
      enum "ANKD000FAN00" {
        value 48;
        description
          "ANKD000FAN00.";
      }
      enum "NEDD000FAN00" {
        value 49;
        description
          "NEDD000FAN00.";
      }
      enum "TNCM000PIU00" {
        value 50;
        description
          "TNCM000PIU00.";
      }
      enum "NECD001FAN00" {
        value 51;
        description
          "NECD001FAN00.";
      }
      enum "ANGD000FAN00" {
        value 52;
        description
          "ANGD000FAN00.";
      }
      enum "ANJ1FAN" {
        value 53;
        description
          "ANJ1FAN.";
      }
      enum "ANJD00CXPA01" {
        value 54;
        description
          "ANJD00CXPA01.";
      }
      enum "ANJ0002CXP00" {
        value 55;
        description
          "ANJ0002CXP00.";
      }
      enum "ANJE000FAN00" {
        value 56;
        description
          "ANJE000FAN00.";
      }
      enum "ANJ0000PIU00" {
        value 57;
        description
          "ANJ0000PIU00.";
      }
      enum "ANJ000APIU00" {
        value 58;
        description
          "ANJ000APIU00.";
      }
      enum "NE05E-SQ" {
        value 59;
        description
          "NE05E-SQ.";
      }
      enum "NE08E-S6E" {
        value 60;
        description
          "NE08E-S6E.";
      }
      enum "ATN910B" {
        value 61;
        description
          "ATN 910B chassis.";
      }
      enum "ATN910B-D" {
        value 62;
        description
          "ATN 910B-D chassis.";
      }
      enum "ATN910B-E" {
        value 63;
        description
          "ATN 910B-E chassis.";
      }
      enum "ATN910B-F" {
        value 64;
        description
          "ATN 910B-F chassis.";
      }
      enum "ADDD00CXPA02" {
        value 65;
        description
          "ADDD00CXPA02.";
      }
      enum "ANDD00CXPB02" {
        value 66;
        description
          "ANDD00CXPB02.";
      }
      enum "ANDD00CXPE02" {
        value 67;
        description
          "ANDD00CXPE02.";
      }
      enum "ANGM000HSA00" {
        value 68;
        description
          "ANGM000HSA00.";
      }
      enum "ANGM000HSB00" {
        value 69;
        description
          "ANGM000HSB00.";
      }
      enum "ANGM0HSDNA02" {
        value 70;
        description
          "ANGM0HSDNA02.";
      }
      enum "ANGM0HSDND00" {
        value 71;
        description
          "ANGM0HSDND00.";
      }
      enum "ANGM0HSDNA01" {
        value 72;
        description
          "ANGM0HSDNA01.";
      }
      enum "ANGM01HSDD00" {
        value 73;
        description
          "ANGM01HSDD00.";
      }
      enum "ANGM02HSDA00" {
        value 74;
        description
          "ANGM02HSDA00.";
      }
      enum "ANGM01HSDD01" {
        value 75;
        description
          "ANGM01HSDD01.";
      }
      enum "ANGM02HSDA01" {
        value 76;
        description
          "ANGM02HSDA01.";
      }
      enum "ATN950B" {
        value 77;
        description
          "ATN 950B chassis.";
      }
      enum "NECMHSTA0211" {
        value 78;
        description
          "NECMHSTA0211.";
      }
      enum "NECMHSTB0211" {
        value 79;
        description
          "NECMHSTB0211.";
      }
      enum "NEDD00CXPA00" {
        value 80;
        description
          "NEDD00CXPA00.";
      }
      enum "CR2D00MPAA90" {
        value 81;
        description
          "CR2D00MPAA90.";
      }
      enum "CR2D000SA890" {
        value 82;
        description
          "CR2D000SA890.";
      }
      enum "CR2D00MP8A90" {
        value 83;
        description
          "CR2D00MP8A90.";
      }
      enum "NEDD01MPAA00" {
        value 84;
        description
          "NEDD01MPAA00.";
      }
      enum "NEDD001SA800" {
        value 85;
        description
          "NEDD001SA800.";
      }
      enum "NEDD01MP8A00" {
        value 86;
        description
          "NEDD01MP8A00.";
      }
      enum "NEDD001EM600" {
        value 87;
        description
          "NEDD001EM600.";
      }
      enum "CR2D000EM890" {
        value 88;
        description
          "CR2D000EM890.";
      }
      enum "CR5D00E4XF20" {
        value 89;
        description
          "CR5D00E4XF20.";
      }
      enum "CR5D00E1NB20" {
        value 90;
        description
          "CR5D00E1NB20.";
      }
      enum "CR5DE2NE4X10" {
        value 91;
        description
          "CR5DE2NE4X10.";
      }
      enum "CR2D0EM4TP10" {
        value 92;
        description
          "CR2D0EM4TP10.";
      }
      enum "CX68E2NLHXF0" {
        value 93;
        description
          "CX68E2NLHXF0.";
      }
      enum "CX68EENEFYFA" {
        value 94;
        description
          "CX68EENEFYFA.";
      }
      enum "CR5D00T1NC70" {
        value 95;
        description
          "CR5D00T1NC70.";
      }
      enum "CR9D00EANB81" {
        value 96;
        description
          "CR9D00EANB81.";
      }
      enum "CR58EANBA" {
        value 97;
        description
          "CR58EANBA.";
      }
      enum "CR9D00EANB80" {
        value 98;
        description
          "CR9D00EANB80.";
      }
      enum "ANDD0032E100" {
        value 99;
        description
          "ANDD0032E100.";
      }
      enum "NEDD32E1M001" {
        value 100;
        description
          "NEDD32E1M001.";
      }
      enum "ANCD000FAN00" {
        value 101;
        description
          "ANCD000FAN00.";
      }
      enum "ANCD000PIU00" {
        value 102;
        description
          "ANCD000PIU00.";
      }
      enum "ANCD00APIU00" {
        value 103;
        description
          "ANCD00APIU00.";
      }
      enum "ANDD000FAN02" {
        value 104;
        description
          "ANDD000FAN02.";
      }
      enum "ANDD002PIU00" {
        value 105;
        description
          "ANDD002PIU00.";
      }
      enum "CR2D00EEGF10" {
        value 106;
        description
          "CR2D00EEGF10.";
      }
      enum "CR5D00EEGF70" {
        value 107;
        description
          "CR5D00EEGF70.";
      }
      enum "CR57E8NCB0" {
        value 108;
        description
          "CR57E8NCB0.";
      }
      enum "ME0D00E8GE71" {
        value 109;
        description
          "ME0D00E8GE71.";
      }
      enum "ME0D00EAGF70" {
        value 110;
        description
          "ME0D00EAGF70.";
      }
      enum "ME0D00L4XF72" {
        value 111;
        description
          "ME0D00L4XF72.";
      }
      enum "ME0DL1XE8G71" {
        value 112;
        description
          "ME0DL1XE8G71.";
      }
      enum "ME0D00L2XF71" {
        value 113;
        description
          "ME0D00L2XF71.";
      }
      enum "ME0D00L4XF70" {
        value 114;
        description
          "ME0D00L4XF70.";
      }
      enum "ME0DL1XE8G70" {
        value 115;
        description
          "ME0DL1XE8G70.";
      }
      enum "ME0D00L2XF70" {
        value 116;
        description
          "ME0D00L2XF70.";
      }
      enum "ME0D00E8GF71" {
        value 117;
        description
          "ME0D00E8GF71.";
      }
      enum "ME0D00E8GE70" {
        value 118;
        description
          "ME0D00E8GE70.";
      }
      enum "ME0D00C4CF71" {
        value 119;
        description
          "ME0D00C4CF71.";
      }
      enum "ME0D000IE170" {
        value 120;
        description
          "ME0D000IE170.";
      }
      enum "ME0D000IE171" {
        value 121;
        description
          "ME0D000IE171.";
      }
      enum "ME0D000DE170" {
        value 122;
        description
          "ME0D000DE170.";
      }
      enum "ME0D000DE171" {
        value 123;
        description
          "ME0D000DE171.";
      }
      enum "ME0D00P4CF70" {
        value 124;
        description
          "ME0D00P4CF70.";
      }
      enum "ME0DP2C1HF70" {
        value 125;
        description
          "ME0DP2C1HF70.";
      }
      enum "ME0D00AUXQ10" {
        value 126;
        description
          "ME0D00AUXQ10.";
      }
      enum "ME0D08CWDM70" {
        value 127;
        description
          "ME0D08CWDM70.";
      }
      enum "ME0D00C4T370" {
        value 128;
        description
          "ME0D00C4T370.";
      }
      enum "ME0D0EAGFH70" {
        value 129;
        description
          "ME0D0EAGFH70.";
      }
      enum "ME0D0L2XFH71" {
        value 130;
        description
          "ME0D0L2XFH71.";
      }
      enum "ME2D00E8GE12" {
        value 131;
        description
          "ME2D00E8GE12.";
      }
      enum "ME2D00EAGF10" {
        value 132;
        description
          "ME2D00EAGF10.";
      }
      enum "ME2D00L4XF11" {
        value 133;
        description
          "ME2D00L4XF11.";
      }
      enum "ME2DL1XE8G11" {
        value 134;
        description
          "ME2DL1XE8G11.";
      }
      enum "ME2D00L2XF12" {
        value 135;
        description
          "ME2D00L2XF12.";
      }
      enum "CR5D00P2XX72" {
        value 136;
        description
          "CR5D00P2XX72.";
      }
      enum "CR57L4XEBG0" {
        value 137;
        description
          "CR57L4XEBG0.";
      }
      enum "CR57TBXF00" {
        value 138;
        description
          "CR57TBXF00.";
      }
      enum "CR57T6XF00" {
        value 139;
        description
          "CR57T6XF00.";
      }
      enum "CR5D00T1MC60" {
        value 140;
        description
          "CR5D00T1MC60.";
      }
      enum "CR5D00TBXF70" {
        value 141;
        description
          "CR5D00TBXF70.";
      }
      enum "CX6D00MPUD11" {
        value 142;
        description
          "CX6D00MPUD11.";
      }
      enum "CX6D00MPUD30" {
        value 143;
        description
          "CX6D00MPUD30.";
      }
      enum "CX6D0SRUA611" {
        value 144;
        description
          "CX6D0SRUA611.";
      }
      enum "CX6DSFUIA07C" {
        value 145;
        description
          "CX6DSFUIA07C.";
      }
      enum "CX6DL2XEIG1B" {
        value 146;
        description
          "CX6DL2XEIG1B.";
      }
      enum "CX6DL4XEBG1B" {
        value 147;
        description
          "CX6DL4XEBG1B.";
      }
      enum "CX6D0L5XFA11" {
        value 148;
        description
          "CX6D0L5XFA11.";
      }
      enum "CR5D0EFGFA73" {
        value 149;
        description
          "CR5D0EFGFA73.";
      }
      enum "CR5DL1XEDG70" {
        value 150;
        description
          "CR5DL1XEDG70.";
      }
      enum "CX6D0LAXFA11" {
        value 151;
        description
          "CX6D0LAXFA11.";
      }
      enum "CX6DISUF5010" {
        value 152;
        description
          "CX6DISUF5010.";
      }
      enum "CR5DLPUF5071" {
        value 153;
        description
          "CR5DLPUF5071.";
      }
      enum "CR5DLPUF507M" {
        value 154;
        description
          "CR5DLPUF507M.";
      }
      enum "CX6DISUF5011" {
        value 155;
        description
          "CX6DISUF5011.";
      }
      enum "CX6DL1XEDG1A" {
        value 156;
        description
          "CX6DL1XEDG1A.";
      }
      enum "CX6D0EFGFA12" {
        value 157;
        description
          "CX6D0EFGFA12.";
      }
      enum "CX6D0EMGFA10" {
        value 158;
        description
          "CX6D0EMGFA10.";
      }
      enum "ME0DMSUFF070" {
        value 159;
        description
          "ME0DMSUFF070.";
      }
      enum "CR5D00E2NC76" {
        value 160;
        description
          "CR5D00E2NC76.";
      }
      enum "CR5D00LEXF76" {
        value 161;
        description
          "CR5D00LEXF76.";
      }
      enum "CR5DE1NLAX76" {
        value 162;
        description
          "CR5DE1NLAX76.";
      }
      enum "CR5D00E2NC75" {
        value 163;
        description
          "CR5D00E2NC75.";
      }
      enum "CR5D00LEXF75" {
        value 164;
        description
          "CR5D00LEXF75.";
      }
      enum "CR5DLPUFE07B" {
        value 165;
        description
          "CR5DLPUFE07B.";
      }
      enum "CR5DLPUFE071" {
        value 166;
        description
          "CR5DLPUFE071.";
      }
      enum "CR5DLPUFE07C" {
        value 167;
        description
          "CR5DLPUFE07C.";
      }
      enum "CR5DE1NLAX75" {
        value 168;
        description
          "CR5DE1NLAX75.";
      }
      enum "CR5D0E6MFA70" {
        value 169;
        description
          "CR5D0E6MFA70.";
      }
      enum "CR5D0E6MFA71" {
        value 170;
        description
          "CR5D0E6MFA71.";
      }
      enum "CR5D00T6XF70" {
        value 171;
        description
          "CR5D00T6XF70.";
      }
      enum "CR53CFE10" {
        value 172;
        description
          "CR53CFE10.";
      }
      enum "CR5D00C2CF70" {
        value 173;
        description
          "CR5D00C2CF70.";
      }
      enum "CR5D00C4CF70" {
        value 174;
        description
          "CR5D00C4CF70.";
      }
      enum "CR5D00C8CF71" {
        value 175;
        description
          "CR5D00C8CF71.";
      }
      enum "CX6D00C8CF10" {
        value 176;
        description
          "CX6D00C8CF10.";
      }
      enum "CX6D0L2XFA10" {
        value 177;
        description
          "CX6D0L2XFA10.";
      }
      enum "CR57L3XFB0" {
        value 178;
        description
          "CR57L3XFB0.";
      }
      enum "CR57L2XFB2" {
        value 179;
        description
          "CR57L2XFB2.";
      }
      enum "CR57L4XFB2" {
        value 180;
        description
          "CR57L4XFB2.";
      }
      enum "CR57EFGFC0" {
        value 181;
        description
          "CR57EFGFC0.";
      }
      enum "CR57L1XEDG0" {
        value 182;
        description
          "CR57L1XEDG0.";
      }
      enum "ME0D0LBXXB7H" {
        value 183;
        description
          "ME0D0LBXXB7H.";
      }
      enum "ME0D2L1NXB7H" {
        value 184;
        description
          "ME0D2L1NXB7H.";
      }
      enum "ME0D0L1NXB7H" {
        value 185;
        description
          "ME0D0L1NXB7H.";
      }
      enum "CX6D0E2NCA10" {
        value 186;
        description
          "CX6D0E2NCA10.";
      }
      enum "CR5D00EDYB70" {
        value 187;
        description
          "CR5D00EDYB70.";
      }
      enum "CR57E8YFA0" {
        value 188;
        description
          "CR57E8YFA0.";
      }
      enum "CR57LKXFB0" {
        value 189;
        description
          "CR57LKXFB0.";
      }
      enum "CR56LFXFB3" {
        value 190;
        description
          "CR56LFXFB3.";
      }
      enum "CR58LPXFA0" {
        value 191;
        description
          "CR58LPXFA0.";
      }
      enum "CX6D0LFXFA11" {
        value 192;
        description
          "CX6D0LFXFA11.";
      }
      enum "ME0D0LAXFE7H" {
        value 193;
        description
          "ME0D0LAXFE7H.";
      }
      enum "ME0D0LAXFB7H" {
        value 194;
        description
          "ME0D0LAXFB7H.";
      }
      enum "ME0D0LAXFH7H" {
        value 195;
        description
          "ME0D0LAXFH7H.";
      }
      enum "ME0DE4NE8V70" {
        value 196;
        description
          "ME0DE4NE8V70.";
      }
      enum "CR5DE4NE8V70" {
        value 197;
        description
          "CR5DE4NE8V70.";
      }
     enum "CX6DE4NE8V10" {
        value 198;
        description
          "CX6DE4NE8V10.";
      }
     enum "CX6D0EDYFA10" {
        value 199;
        description
          "CX6D0EDYFA10.";
      }
      enum "CR57LAXFB1" {
        value 200;
        description
          "CR57LAXFB1.";
      }
      enum "CR57L5XFB2" {
        value 201;
        description
          "CR57L5XFB2.";
      }
      enum "CR57EMGFC0" {
        value 202;
        description
          "CR57EMGFC0.";
      }
      enum "CR57L2XEIG0" {
        value 203;
        description
          "CR57L2XEIG0.";
      }
      enum "CR57L5XFC0" {
        value 204;
        description
          "CR57L5XFC0.";
      }
      enum "ME0D0L5XXE7H" {
        value 205;
        description
          "ME0D0L5XXE7H.";
      }
      enum "ME0D0L6XXB7H" {
        value 206;
        description
          "ME0D0L6XXB7H.";
      }
      enum "ME0D0L2XXE7H" {
        value 207;
        description
          "ME0D0L2XXE7H.";
      }
      enum "ME0D0L5XXE7F" {
        value 208;
        description
          "ME0D0L5XXE7F.";
      }
      enum "ME0D0EFGFE7H" {
        value 209;
        description
          "ME0D0EFGFE7H.";
      }
      enum "ME0D0L2XXB7H" {
        value 210;
        description
          "ME0D0L2XXB7H.";
      }
      enum "ME0D0L5XXB7F" {
        value 211;
        description
          "ME0D0L5XXB7F.";
      }
      enum "ME0D0L5XXB7H" {
        value 212;
        description
          "ME0D0L5XXB7H.";
      }
      enum "ME0D0EFGFB7H" {
        value 213;
        description
          "ME0D0EFGFB7H.";
      }
      enum "CR57D2NT00" {
        value 214;
        description
          "CR57D2NT00.";
      }
      enum "CR53P8CF0" {
        value 215;
        description
          "CR53P8CF0.";
      }
      enum "CR53P4CF0" {
        value 216;
        description
          "CR53P4CF0.";
      }
      enum "CR5D00P2CF70" {
        value 217;
        description
          "CR5D00P2CF70.";
      }
      enum "CR2D00E1MF70" {
        value 218;
        description
          "CR2D00E1MF70.";
      }
      enum "CR2D00T4XF70" {
        value 219;
        description
          "CR2D00T4XF70.";
      }
      enum "CR5D00E1MF70" {
        value 220;
        description
          "CR5D00E1MF70.";
      }
      enum "CR5D00T4XF70" {
        value 221;
        description
          "CR5D00T4XF70.";
      }
      enum "CR5D00L4XEKGFB71" {
        value 222;
        description
          "CR5D00L4XEKGFB71.";
      }
      enum "CR5D00L2XEFGFA71" {
        value 223;
        description
          "CR5D00L2XEFGFA71.";
      }
      enum "CR5D00AUXQ10" {
        value 224;
        description
          "CR5D00AUXQ10.";
      }
      enum "CR5M0E8GFA30" {
        value 225;
        description
          "CR5M0E8GFA30.";
      }
      enum "CR5D0L2XFA70" {
        value 226;
        description
          "CR5D0L2XFA70.";
      }
      enum "CR5D0L5XFA72" {
        value 227;
        description
          "CR5D0L5XFA72.";
      }
    enum "CR5D0LBXFE7E" {
       value 228;
        description
         "CR5D0LBXFE7E.";
      }
    enum "CR5D00L1NC7E" {
        value 229;
        description
          "CR5D00L1NC7E.";
      }
      enum "ME0D00L1NC7E" {
        value 230;
        description
          "ME0D00L1NC7E.";
      }
      enum "ME0D0LBXFE7E" {
        value 231;
        description
          "ME0D0LBXFE7E.";
      }
      enum "CR5D0LAXFE70" {
        value 232;
        description
          "CR5D0LAXFE70.";
      }
      enum "CR5D00LAXF70" {
        value 233;
        description
          "CR5D00LAXF70.";
      }
      enum "CR5D0L5XFA70" {
        value 234;
        description
          "CR5D0L5XFA70.";
      }
      enum "CR5D0EEGEA70" {
        value 235;
        description
          "CR5D0EEGEA70.";
      }
      enum "CR5D00P4CF70" {
        value 236;
        description
          "CR5D00P4CF70.";
      }
      enum "CR2D00L2XF12" {
        value 237;
        description
          "CR2D00L2XF12.";
      }
      enum "CX6D00L2XF11" {
        value 238;
        description
          "CX6D00L2XF11.";
      }
      enum "CR5D00L2XF71" {
        value 239;
        description
          "CR5D00L2XF71.";
      }
      enum "CR2D0L2XFH10" {
        value 240;
        description
          "CR2D0L2XFH10.";
      }
      enum "CR5D0L2XFH71" {
        value 241;
        description
          "CR5D0L2XFH71.";
      }
      enum "CR2D00E8GE12" {
        value 242;
        description
          "CR2D00E8GE12.";
      }
      enum "CARD ATN 905" {
        value 243;
        description
          "CARD ATN 905.";
      }
      enum "CX68E4NLAXF0" {
        value 244;
        description
          "CX68E4NLAXF0.";
      }
      enum "CARD ATN 910C-F" {
        value 245;
        description
          "CARD ATN 910C-F.";
      }
     enum "CARD ATN 910C-E" {
        value 246;
        description
          "CARD ATN 910C-E.";
      }
      enum "CARD ETN500-F" {
        value 247;
        description
          "CARD ETN500-F.";
      }
      enum "CARD NE05E-SR" {
        value 248;
        description
          "CARD NE05E-SR.";
      }
      enum "CX6D00E8GE11" {
        value 249;
        description
          "CX6D00E8GE11.";
      }
      enum "CR5D00E8GE71" {
        value 250;
        description
          "CR5D00E8GE71.";
      }
      enum "CR2DL1XE8G11" {
        value 251;
        description
          "CR2DL1XE8G11.";
      }
      enum "CX6DL1XE8G11" {
        value 252;
        description
          "CX6DL1XE8G11.";
      }
      enum "CR5DL1XE8G71" {
        value 253;
        description
          "CR5DL1XE8G71.";
      }
      enum "CR2D00L4XF11" {
        value 254;
        description
          "CR2D00L4XF11.";
      }
      enum "CX6D00L4XF11" {
        value 255;
        description
          "CX6D00L4XF11.";
      }
      enum "CR5D00L4XF71" {
        value 256;
        description
          "CR5D00L4XF71.";
      }
      enum "CR5D00L4XF72" {
        value 257;
        description
          "CR5D00L4XF72.";
      }
      enum "CR2D00EAGF10" {
        value 258;
        description
          "CR2D00EAGF10.";
      }
      enum "CX6D00EAGF10" {
        value 259;
        description
          "CX6D00EAGF10.";
      }
      enum "CR5D00EAGF70" {
        value 260;
        description
          "CR5D00EAGF70.";
      }
      enum "CR2D0EAGFH10" {
        value 261;
        description
          "CR2D0EAGFH10.";
      }
      enum "CR5D0EAGFH70" {
        value 262;
        description
          "CR5D0EAGFH70.";
      }
      enum "chassis" {
        value 263;
        description
          "Chassis.";
      }
      enum "boardSlot" {
        value 264;
        description
          "Board slot.";
      }
      enum "mpuSlot" {
        value 265;
        description
          "MPU slot.";
      }
      enum "lpuSlot" {
        value 266;
        description
          "LPU slot.";
      }
      enum "sfuSlot" {
        value 267;
        description
          "SFU slot.";
      }
      enum "icuSlot" {
        value 268;
        description
          "ICU slot.";
      }
      enum "ecuSlot" {
        value 269;
        description
          "ECU slot.";
      }
      enum "clkSlot" {
        value 270;
        description
          "CLK slot.";
      }
      enum "fanSlot" {
        value 271;
        description
          "Fan slot.";
      }
      enum "powerSlot" {
        value 272;
        description
          "Power slot.";
      }
      enum "PmuSlot" {
        value 273;
        description
          "PMU slot.";
      }
      enum "pmuSlot" {
        value 274;
        description
          "PMU slot.";
      }
      enum "pduSlot" {
        value 275;
        description
          "PDU slot.";
      }
      enum "picSlot" {
        value 276;
        description
          "Pic slot.";
      }
      enum "ofcSlot" {
        value 277;
        description
          "Ofc slot.";
      }
      enum "lcdSlot" {
        value 278;
        description
          "LCD slot.";
      }
      enum "cfcardSlot" {
        value 279;
        description
          "CF card slot.";
      }
      enum "cmuSlot" {
        value 280;
        description
          "CMU slot.";
      }
      enum "virtualSubSlot" {
        value 281;
        description
          "Virtual sub slot.";
      }
      enum "virtualSlot" {
        value 282;
        description
          "Virtual slot.";
      }
      enum "fname8090Unknown" {
        value 283;
        description
          "Unknown.";
      }
      enum "fname8090Whole" {
        value 284;
        description
          "NE5000E chassis.";
      }
      enum "fname8090NE5000EX16" {
        value 285;
        description
          "NE5000EX chassis.";
      }
      enum "fname8090ClusterCentral" {
        value 286;
        description
          "NE5000E cluster central chassis.";
      }
      enum "fname8090NE5000EX-VB" {
        value 287;
        description
          "NE5000EX-VB chassis.";
      }
      enum "fname8090NE5000EX16A" {
        value 288;
        description
          "NE5000EX16A Chassis.";
      }
      enum "fname8090NE5000EX16B" {
        value 289;
        description
          "NE5000EX16B Chassis.";
      }
      enum "fname8090NE40E-X16B" {
        value 290;
        description
          "NE40E-X16B Chassis.";
      }
      enum "fname8090NE5000ECCC-A" {
        value 291;
        description
          "NE5000ECCC-A Chassis.";
      }
      enum "CE585048T4S2QEI" {
        value 292;
        description
          "CE585048T4S2QEI chassis.";
      }
      enum "CE685048S4QEI" {
        value 293;
        description
          "CE685048S4QEI chassis.";
      }
      enum "CE685048T4QEI" {
        value 294;
        description
          "CE685048T4QEI chassis.";
      }
      enum "CR52MPUA" {
        value 295;
        description
          "CR52MPUA.";
      }
      enum "CR52MPUB" {
        value 296;
        description
          "CR52MPUB.";
      }
      enum "CR55MPUA" {
        value 297;
        description
          "CR55MPUA.";
      }
      enum "CR55MPUAB" {
        value 298;
        description
          "CR55MPUAB.";
      }
      enum "CR56RPUA" {
        value 299;
        description
          "CR56RPUA.";
      }
      enum "CR52LPUA" {
        value 300;
        description
          "CR52LPUA.";
      }
      enum "CR57E8NC" {
        value 301;
        description
          "CR57E8NC.";
      }
      enum "CR52LPUB" {
        value 302;
        description
          "CR52LPUB.";
      }
      enum "CR52LPUC" {
        value 303;
        description
          "CR52LPUC.";
      }
      enum "CR52LPUE" {
        value 304;
        description
          "CR52LPUE.";
      }
      enum "CR52LPUR" {
        value 305;
        description
          "CR52LPUR.";
      }
      enum "CR52LPUF" {
        value 306;
        description
          "CR52LPUF.";
      }
      enum "CR52LPUG" {
        value 307;
        description
          "CR52LPUG.";
      }
      enum "CR52LPUH" {
        value 308;
        description
          "CR52LPUH.";
      }
      enum "CR52LPUI" {
        value 309;
        description
          "CR52LPUI.";
      }
      enum "CR52LPUK" {
        value 310;
        description
          "CR52LPUK.";
      }
      enum "CR52LPUM" {
        value 311;
        description
          "CR52LPUM.";
      }
      enum "CR52LPUN" {
        value 312;
        description
          "CR52LPUN.";
      }
      enum "CR52SPUC" {
        value 313;
        description
          "CR52SPUC.";
      }
      enum "CR56LPUF100A" {
        value 314;
        description
          "CR56LPUF100A.";
      }
      enum "CR56LPUF100B" {
        value 315;
        description
          "CR56LPUF100B.";
      }
      enum "CR56LPUI100A" {
        value 316;
        description
          "CR56LPUI100A.";
      }
      enum "CR56LPUI100B" {
        value 317;
        description
          "CR56LPUI100B.";
      }
      enum "CR56LPUI100C" {
        value 318;
        description
          "CR56LPUI100C.";
      }
      enum "CR56LPUF200A" {
        value 319;
        description
          "CR56LPUF200A.";
      }
      enum "RNRLPUB" {
        value 320;
        description
          "RNRLPUB.";
      }
      enum "RNRLPUD" {
        value 321;
        description
          "RNRLPUD.";
      }
      enum "RNRLPUF" {
        value 322;
        description
          "RNRLPUF.";
      }
      enum "RNRNS" {
        value 323;
        description
          "RNRNS.";
      }
      enum "RNRGRE" {
        value 324;
        description
          "RNRGRE.";
      }
      enum "CR52SFUA" {
        value 325;
        description
          "CR52SFUA.";
      }
      enum "CR52SRUA" {
        value 326;
        description
          "CR52SRUA.";
      }
      enum "CR52SFUD" {
        value 327;
        description
          "CR52SFUD.";
      }
      enum "CR52SFUF" {
        value 328;
        description
          "CR52SFUF.";
      }
      enum "CR52SFUG" {
        value 329;
        description
          "CR52SFUG.";
      }
      enum "CR52SFUC" {
        value 330;
        description
          "CR52SFUC.";
      }
      enum "CR52SFEA" {
        value 331;
        description
          "CR52SFEA.";
      }
      enum "CR52K-SFEA" {
        value 332;
        description
          "CR52K-SFEA.";
      }
      enum "CR55SFUA" {
        value 333;
        description
          "CR55SFUA.";
      }
      enum "CR55ECUA" {
        value 334;
        description
          "CR55ECUA.";
      }
      enum "CR55C-ECUA" {
        value 335;
        description
          "CR55C-ECUA.";
      }
      enum "CR55ICUA" {
        value 336;
        description
          "CR55ICUA.";
      }
      enum "CR56SFUF100B" {
        value 337;
        description
          "CR56SFUF100B.";
      }
      enum "CR55SFUI100A" {
        value 338;
        description
          "CR55SFUI100A.";
      }
      enum "CR56SFUF100C" {
        value 339;
        description
          "CR56SFUF100C.";
      }
      enum "CR56SFU200A" {
        value 340;
        description
          "CR56SFU200A.";
      }
      enum "CR56SFU400A" {
        value 341;
        description
          "CR56SFU400A.";
      }
      enum "CR55MPUA5" {
        value 342;
        description
          "CR55MPUA5.";
      }
      enum "CR55ICUB" {
        value 343;
        description
          "CR55ICUB.";
      }
      enum "CR55SFUF400A" {
        value 344;
        description
          "CR55SFUF400A.";
      }
      enum "CR55SFUI400B" {
        value 345;
        description
          "CR55SFUI400B.";
      }
      enum "CR55SFUI400C" {
        value 346;
        description
          "CR55SFUI400C.";
      }
      enum "CR55ECU100A" {
        value 347;
        description
          "CR55ECU100A.";
      }
      enum "CR52SFEB" {
        value 348;
        description
          "CR52SFEB.";
      }
      enum "DE51SRU1A" {
        value 349;
        description
          "DE51SRU1A.";
      }
      enum "DE51SRU1B" {
        value 350;
        description
          "DE51SRU1B.";
      }
      enum "DE51SRU1C" {
        value 351;
        description
          "DE51SRU1C.";
      }
      enum "CR5DSFUFA06C" {
        value 352;
        description
          "CR5DSFUFA06C.";
      }
      enum "CR5DSFUIK06A" {
        value 353;
        description
          "CR5DSFUIK06A.";
      }
      enum "CR5D0MPUA550" {
        value 354;
        description
          "CR5D0MPUA550.";
      }
      enum "CR5D00ICUB50" {
        value 355;
        description
          "CR5D00ICUB50.";
      }
      enum "CR5DSFUFK050" {
        value 356;
        description
          "CR5DSFUFK050.";
      }
      enum "CR5D0MPUA451" {
        value 357;
        description
          "CR5D0MPUA451.";
      }
      enum "CR5D00ICUA51" {
        value 358;
        description
          "CR5D00ICUA51.";
      }
      enum "CR9D0MPUN180" {
        value 359;
        description
          "CR9D0MPUN180.";
      }
      enum "CR9D00E8NC80" {
        value 360;
        description
          "CR9D00E8NC80.";
      }
      enum "CR9D00EFMB80" {
        value 361;
        description
          "CR9D00EFMB80.";
      }
      enum "CR9D0MPUP180" {
        value 362;
        description
          "CR9D0MPUP180.";
      }
      enum "CR9D0SFUT481" {
        value 363;
        description
          "CR9D0SFUT481.";
      }
      enum "CR9D0SFUT48D" {
        value 364;
        description
          "CR9D0SFUT48D.";
      }
      enum "CR9D0SFUT48E" {
        value 365;
        description
          "CR9D0SFUT48E.";
      }
      enum "CR9D0SFUT280" {
        value 366;
        description
          "CR9D0SFUT280.";
      }
      enum "CX6D0MPUP1A0" {
        value 367;
        description
          "CX6D0MPUP1A0.";
      }
      enum "CX6D0MPUP2A0" {
        value 368;
        description
          "CX6D0MPUP2A0.";
      }
      enum "CX6DSFUIT4AA" {
        value 369;
        description
          "CX6DSFUIT4AA.";
      }
      enum "CX6D0MPUN1A0" {
        value 370;
        description
          "CX6D0MPUN1A0.";
      }
      enum "CX6DSFUIT4AB" {
        value 371;
        description
          "CX6DSFUIT4AB.";
      }
      enum "CR9D0SFUTF80" {
        value 372;
        description
          "CR9D0SFUTF80.";
      }
      enum "CR9D0SFUT480" {
        value 373;
        description
          "CR9D0SFUT480.";
      }
      enum "CR9D00EPXF80" {
        value 374;
        description
          "CR9D00EPXF80.";
      }
      enum "CR9D00EDNB80" {
        value 375;
        description
          "CR9D00EDNB80.";
      }
      enum "CR9D000CMU60" {
        value 376;
        description
          "CR9D000CMU60.";
      }
      enum "CR9D00D8NC80" {
        value 377;
        description
          "CR9D00D8NC80.";
      }
      enum "CR5DSFUFK051" {
        value 378;
        description
          "CR5DSFUFK051.";
      }
      enum "CR5DSFUFT050" {
        value 379;
        description
          "CR5DSFUFT050.";
      }
      enum "CR5DSFUIT06H" {
        value 380;
        description
          "CR5DSFUIT06H.";
      }
      enum "CR5D0MPUA750" {
        value 381;
        description
          "CR5D0MPUA750.";
      }
      enum "CR5D0MPUB660" {
        value 382;
        description
          "CR5D0MPUB660.";
      }
      enum "CR5D0MPUB680" {
        value 383;
        description
          "CR5D0MPUB680.";
      }
      enum "CR5DSFUIK06B" {
        value 384;
        description
          "CR5DSFUIK06B.";
      }
      enum "CR5DSFUIK06C" {
        value 385;
        description
          "CR5DSFUIK06C.";
      }
      enum "BOOTROM" {
        value 386;
        description
          "BOOTROM.";
      }
      enum "FLASH" {
        value 387;
        description
          "FLASH.";
      }
      enum "EPLD1" {
        value 388;
        description
          "EPLD1.";
      }
      enum "EPLD2" {
        value 389;
        description
          "EPLD2.";
      }
      enum "CR52E1XX" {
        value 390;
        description
          "CR52E1XX.";
      }
      enum "CR52W1XX" {
        value 391;
        description
          "CR52W1XX.";
      }
      enum "CR2D00C1CF11" {
        value 392;
        description
          "CR2D00C1CF11.";
      }
      enum "CR52EAGF" {
        value 393;
        description
          "CR52EAGF.";
      }
      enum "CR52P4UF" {
        value 394;
        description
          "CR52P4UF.";
      }
      enum "CR52P1XX" {
        value 395;
        description
          "CR52P1XX.";
      }
      enum "CR52P4HF" {
        value 396;
        description
          "CR52P4HF.";
      }
      enum "CR52E2XX" {
        value 397;
        description
          "CR52E2XX.";
      }
      enum "CR52W2XX" {
        value 398;
        description
          "CR52W2XX.";
      }
      enum "CR52P2XX" {
        value 399;
        description
          "CR52P2XX.";
      }
      enum "CR52EMGE" {
        value 400;
        description
          "CR52EMGE.";
      }
      enum "CR52P8CF" {
        value 401;
        description
          "CR52P8CF.";
      }
      enum "CR52EFGE" {
        value 402;
        description
          "CR52EFGE.";
      }
      enum "CR52P1UF" {
        value 403;
        description
          "CR52P1UF.";
      }
      enum "CR52P2UF" {
        value 404;
        description
          "CR52P2UF.";
      }
      enum "CR52E5GF" {
        value 405;
        description
          "CR52E5GF.";
      }
      enum "CR52P4CF" {
        value 406;
        description
          "CR52P4CF.";
      }
      enum "CR53P1MZ" {
        value 407;
        description
          "CR53P1MZ.";
      }
      enum "CR52D1MV" {
        value 408;
        description
          "CR52D1MV.";
      }
      enum "CR52E4XX" {
        value 409;
        description
          "CR52E4XX.";
      }
      enum "CR56P2XX" {
        value 410;
        description
          "CR56P2XX.";
      }
      enum "CR56L2XX" {
        value 411;
        description
          "CR56L2XX.";
      }
      enum "CR56E2XX" {
        value 412;
        description
          "CR56E2XX.";
      }
      enum "CR56D2XX" {
        value 413;
        description
          "CR56D2XX.";
      }
      enum "CR56L5XX" {
        value 414;
        description
          "CR56L5XX.";
      }
      enum "CR56E5XX" {
        value 415;
        description
          "CR56E5XX.";
      }
      enum "CR56P1MZ" {
        value 416;
        description
          "CR56P1MZ.";
      }
      enum "CR56E1NC" {
        value 417;
        description
          "CR56E1NC.";
      }
      enum "CR56EFGF" {
        value 418;
        description
          "CR56EFGF.";
      }
      enum "CR52EKGFY" {
        value 419;
        description
          "CR52EKGFY.";
      }
      enum "CR57EFGF" {
        value 420;
        description
          "CR57EFGF.";
      }
      enum "CR56E1NCC" {
        value 421;
        description
          "CR56E1NCC.";
      }
      enum "CR52P1XZ" {
        value 422;
        description
          "CR52P1XZ.";
      }
      enum "CR52E1XZ" {
        value 423;
        description
          "CR52E1XZ.";
      }
      enum "CR52W1XZ" {
        value 424;
        description
          "CR52W1XZ.";
      }
      enum "CR56E2ND" {
        value 425;
        description
          "CR56E2ND.";
      }
      enum "CR56E6MB" {
        value 426;
        description
          "CR56E6MB.";
      }
      enum "CR56LEXF" {
        value 427;
        description
          "CR56LEXF.";
      }
      enum "CR56E1NCB" {
        value 428;
        description
          "CR56E1NCB.";
      }
      enum "CR56LFXF" {
        value 429;
        description
          "CR56LFXF.";
      }
      enum "CR56LFXF0" {
        value 430;
        description
          "CR56LFXF0.";
      }
      enum "CR56L5XFB" {
        value 431;
        description
          "CR56L5XFB.";
      }
      enum "CR56E5XFB" {
        value 432;
        description
          "CR56E5XFB.";
      }
      enum "CR56P8UF" {
        value 433;
        description
          "CR56P8UF.";
      }
      enum "CR56E2NCC" {
        value 434;
        description
          "CR56E2NCC.";
      }
      enum "CR56E5MB" {
        value 435;
        description
          "CR56E5MB.";
      }
      enum "SPU" {
        value 436;
        description
          "SPU.";
      }
      enum "TSUA" {
        value 437;
        description
          "TSUA.";
      }
      enum "CR56E1MC" {
        value 438;
        description
          "CR56E1MC.";
      }
      enum "CR56LAXFA" {
        value 439;
        description
          "CR56LAXFA.";
      }
      enum "CR55OFCA" {
        value 440;
        description
          "CR55OFCA.";
      }
      enum "CR57LFXFE" {
        value 441;
        description
          "CR57LFXFE.";
      }
      enum "CR57E2NCE" {
        value 442;
        description
          "CR57E2NCE.";
      }
      enum "CR55C-OFCA" {
        value 443;
        description
          "CR55C-OFCA.";
      }
      enum "CR52OFCB" {
        value 444;
        description
          "CR52OFCB.";
      }
      enum "CR55OFC40" {
        value 445;
        description
          "CR55OFC40.";
      }
      enum "CR55OFC100A" {
        value 446;
        description
          "CR55OFC100A.";
      }
      enum "CR55OFC100B" {
        value 447;
        description
          "CR55OFC100B.";
      }
      enum "CR55OFC400A" {
        value 448;
        description
          "CR55OFC400A.";
      }
      enum "CR5M0OFCK050" {
        value 449;
        description
          "CR5M0OFCK050.";
      }
      enum "CR55OFC1TA" {
        value 450;
        description
          "CR55OFC1TA.";
      }
      enum "CR5D0OFCT050" {
        value 451;
        description
          "CR5D0OFCT050.";
      }
      enum "CR55OFC400D" {
        value 452;
        description
          "CR55OFC400D.";
      }
      enum "CR5D0OFCK051" {
        value 453;
        description
          "CR5D0OFCK051.";
      }
      enum "CR55OFC400B" {
        value 454;
        description
          "CR55OFC400B.";
      }
      enum "CR55OFC1TB" {
        value 455;
        description
          "CR55OFC1TB.";
      }
      enum "CR55OFC2TA" {
        value 456;
        description
          "CR55OFC2TA.";
      }
      enum "CR55OFC2TB" {
        value 457;
        description
          "CR55OFC2TB.";
      }
      enum "CR50OFC1TC" {
        value 458;
        description
          "CR50OFC1TC.";
      }
      enum "CR50OFC1TD" {
        value 459;
        description
          "CR50OFC1TD.";
      }
      enum "CR52OFCV" {
        value 460;
        description
          "CR52OFCV.";
      }
      enum "Eth" {
        value 461;
        description
          "Ethernet port.";
      }
      enum "Pos" {
        value 462;
        description
          "Pos port.";
      }
      enum "GE" {
        value 463;
        description
          "Gigabit Ethernet port.";
      }
      enum "FE" {
        value 464;
        description
          "FE.";
      }
      enum "10GE" {
        value 465;
        description
          "10GE.";
      }
      enum "GF" {
        value 466;
        description
          "GF.";
      }
      enum "10GF" {
        value 467;
        description
          "10GF.";
      }
      enum "40GF" {
        value 468;
        description
          "40GF.";
      }
      enum "10GFCOM" {
        value 469;
        description
          "10GFCOM.";
      }
      enum "Cpos" {
        value 470;
        description
          "Cpos port.";
      }
      enum "E1" {
        value 471;
        description
          "E1 port.";
      }
      enum "E3" {
        value 472;
        description
          "E3 port.";
      }
      enum "ATM" {
        value 473;
        description
          "Atm Port.";
      }
      enum "PhySerial" {
        value 474;
        description
          "Physical Serial Port.";
      }
      enum "40GFSPLIT" {
        value 475;
        description
          "40GFSPLIT.";
      }
      enum "FlexE" {
        value 476;
        description
          "FlexE.";
      }
      enum "ADMCHANNEL" {
        value 477;
        description
          "Channel.";
      }
      enum "ADMPORT" {
        value 478;
        description
          "LinePort.";
      }
      enum "VSR" {
        value 479;
        description
          "VSR port.";
      }
      enum "FSP" {
        value 480;
        description
          "FSP port.";
      }
      enum "LFE" {
        value 481;
        description
          "LFE.";
      }
      enum "EXTPOWER" {
        value 482;
        description
          "EXTPOWER.";
      }
      enum "POWER" {
        value 483;
        description
          "Power supply.";
      }
      enum "POWER DC" {
        value 484;
        description
          "POWER DC.";
      }
      enum "POWER AC" {
        value 485;
        description
          "POWER AC.";
      }
      enum "PMU" {
        value 486;
        description
          "PMU.";
      }
      enum "PM" {
        value 487;
        description
          "PM.";
      }
      enum "PEM" {
        value 488;
        description
          "PEM.";
      }
      enum "PDU" {
        value 489;
        description
          "PDU.";
      }
      enum "DMU" {
        value 490;
        description
          "DMU.";
      }
      enum "DACS" {
        value 491;
        description
          "DACS.";
      }
      enum "CLOCK" {
        value 492;
        description
          "Clock board.";
      }
      enum "FAN" {
        value 493;
        description
          "Fan.";
      }
      enum "CX67FCBA" {
        value 494;
        description
          "FAN.";
      }
      enum "CX67FCBB" {
        value 495;
        description
          "FAN.";
      }
      enum "CX67FCBB_R" {
        value 496;
        description
          "FAN.";
      }
      enum "CX68FCBC" {
        value 497;
        description
          "FAN.";
      }
      enum "CX68FCBC_NEW" {
        value 498;
        description
          "FAN.";
      }
      enum "CX68FCBD" {
        value 499;
        description
          "FAN.";
      }
      enum "CX68FCBD_R" {
        value 500;
        description
          "FAN.";
      }
      enum "LCD" {
        value 501;
        description
          "LCD.";
      }
      enum "CFCARD" {
        value 502;
        description
          "CF card.";
      }
      enum "CMU" {
        value 503;
        description
          "CMU.";
      }
      enum "CR5D00EKGF60" {
        value 504;
        description
          "CR5D00EKGF60.";
      }
      enum "CR5D00P8UF61" {
        value 505;
        description
          "CR5D00P8UF61.";
      }
      enum "CR5D00E4XX60" {
        value 506;
        description
          "CR5D00E4XX60.";
      }
      enum "CR5D00W4XX60" {
        value 507;
        description
          "CR5D00W4XX60.";
      }
      enum "CR5DLPUFA060" {
        value 508;
        description
          "CR5DLPUFA060.";
      }
      enum "CR5D00LEXF60" {
        value 509;
        description
          "CR5D00LEXF60.";
      }
      enum "CR5D00E2NC60" {
        value 510;
        description
          "CR5D00E2NC60.";
      }
      enum "CR5DE1NLAX60" {
        value 511;
        description
          "CR5DE1NLAX60.";
      }
      enum "CR5DSFEBA06B" {
        value 512;
        description
          "CR5DSFEBA06B.";
      }
      enum "CR5D0MPUB461" {
        value 513;
        description
          "CR5D0MPUB461.";
      }
      enum "CR5DSFUFA06B" {
        value 514;
        description
          "CR5DSFUFA06B.";
      }
      enum "CR5DSFUIE060" {
        value 515;
        description
          "CR5DSFUIE060.";
      }
      enum "CR5D0MPUA450" {
        value 516;
        description
          "CR5D0MPUA450.";
      }
      enum "CR5DECUFA050" {
        value 517;
        description
          "CR5DECUFA050.";
      }
      enum "CR5DSFUIA050" {
        value 518;
        description
          "CR5DSFUIA050.";
      }
      enum "CR5D00L5XX60" {
        value 519;
        description
          "CR5D00L5XX60.";
      }
      enum "CR5D00E5XX60" {
        value 520;
        description
          "CR5D00E5XX60.";
      }
      enum "CR5D00L2XX60" {
        value 521;
        description
          "CR5D00L2XX60.";
      }
      enum "CR5D00E2XX60" {
        value 522;
        description
          "CR5D00E2XX60.";
      }
      enum "CR5D00EFGF60" {
        value 523;
        description
          "CR5D00EFGF60.";
      }
      enum "CR5D00P1MZ60" {
        value 524;
        description
          "CR5D00P1MZ60.";
      }
      enum "CR5D00P2XX60" {
        value 525;
        description
          "CR5D00P2XX60.";
      }
      enum "CR5M00E1MC60" {
        value 526;
        description
          "CR5M00E1MC60.";
      }
      enum "CR5D00E1NC60" {
        value 527;
        description
          "CR5D00E1NC60.";
      }
      enum "CR5D00LAXX60" {
        value 528;
        description
          "CR5D00LAXX60.";
      }
      enum "CR5D00E2NC61" {
        value 529;
        description
          "CR5D00E2NC61.";
      }
      enum "CR5D00E6MF61" {
        value 530;
        description
          "CR5D00E6MF61.";
      }
      enum "CR5D00LEXF61" {
        value 531;
        description
          "CR5D00LEXF61.";
      }
      enum "CR5D00E1NC61" {
        value 532;
        description
          "CR5D00E1NC61.";
      }
      enum "CR5D00L5XF60" {
        value 533;
        description
          "CR5D00L5XF60.";
      }
      enum "CR5D00E5XF60" {
        value 534;
        description
          "CR5D00E5XF60.";
      }
      enum "CR5D00P8UF60" {
        value 535;
        description
          "CR5D00P8UF60.";
      }
      enum "CR5D00E2NC62" {
        value 536;
        description
          "CR5D00E2NC62.";
      }
      enum "CR5D00E5MF61" {
        value 537;
        description
          "CR5D00E5MF61.";
      }
      enum "CR5D0OFCA060" {
        value 538;
        description
          "CR5D0OFCA060.";
      }
      enum "other" {
        value 539;
        description
          "Other.";
      }
      enum "CX6D00MPUK70" {
        value 540;
        description
          "CX6D00MPUK70.";
      }
      enum "CX6PM2EBAS70" {
        value 541;
        description
          "CX6PM2EBAS70.";
      }
      enum "CX6PM2EBAS71" {
        value 542;
        description
          "CX6PM2EBAS71.";
      }
      enum "CX6PM2FBAS70" {
        value 543;
        description
          "CX6PM2FBAS70.";
      }
      enum "CX6PM2FBAS71" {
        value 544;
        description
          "CX6PM2FBAS71.";
      }
      enum "CR2P2EBASD10" {
        value 545;
        description
          "CR2P2EBASD10.";
      }
      enum "CR2P2EBASA10" {
        value 546;
        description
          "CR2P2EBASA10.";
      }
      enum "CR2P2FBASD10" {
        value 547;
        description
          "CR2P2FBASD10.";
      }
      enum "CR2P2FBASA10" {
        value 548;
        description
          "CR2P2FBASA10.";
      }
      enum "CR5PM2EBAS70" {
        value 549;
        description
          "CR5PM2EBAS70.";
      }
      enum "CR5PM2EBAS71" {
        value 550;
        description
          "CR5PM2EBAS71.";
      }
      enum "CR5PM2FBAS70" {
        value 551;
        description
          "CR5PM2FBAS70.";
      }
      enum "CR5PM2FBAS71" {
        value 552;
        description
          "CR5PM2FBAS71.";
      }
      enum "TNRPM2EBAS70" {
        value 553;
        description
          "TNRPM2EBAS70.";
      }
      enum "TNRPM2EBAS71" {
        value 554;
        description
          "TNRPM2EBAS71.";
      }
      enum "TNRPM2FBAS70" {
        value 555;
        description
          "TNRPM2FBAS70.";
      }
      enum "TNRPM2FBAS71" {
        value 556;
        description
          "TNRPM2FBAS71.";
      }
      enum "CR5PM2HBAS72" {
        value 557;
        description
          "CR5PM2HBAS72.";
      }
      enum "CX6PM2KBAS90" {
        value 558;
        description
          "CX6PM2KBAS90.";
      }
      enum "CX6PM2KBAS91" {
        value 559;
        description
          "CX6PM2KBAS91.";
      }
      enum "CX6B0BKP0391" {
        value 560;
        description
          "CX6B0BKP0391.";
      }
      enum "CR5PM2KBAS90" {
        value 561;
        description
          "CR5PM2KBAS90.";
      }
      enum "CR5PM2KBAS91" {
        value 562;
        description
          "CR5PM2KBAS91.";
      }
      enum "CR5B0BKP0391" {
        value 563;
        description
          "CR5B0BKP0391.";
      }
      enum "TNRB0BKP0373" {
        value 564;
        description
          "TNRB0BKP0373.";
      }
      enum "CX6P02ABAS00" {
        value 565;
        description
          "CX6P02ABAS00.";
      }
      enum "CX6P02ABAS01" {
        value 566;
        description
          "CX6P02ABAS01.";
      }
      enum "CX6P020BKP00" {
        value 567;
        description
          "CX6P020BKP00.";
      }
      enum "CX6B0BKP0393" {
        value 568;
        description
          "CX6B0BKP0393.";
      }
      enum "CR5B0BKP0393" {
        value 569;
        description
          "CR5B0BKP0393.";
      }
      enum "CX6P020BKP01" {
        value 570;
        description
          "CX6P020BKP01.";
      }
      enum "TNRB0BKP0374" {
        value 571;
        description
          "TNRB0BKP0374.";
      }
      enum "CR5PM2HBAS73" {
        value 572;
        description
          "CR5PM2HBAS73.";
      }
      enum "CR5B0BKP0377" {
        value 573;
        description
          "CR5B0BKP0377.";
      }
      enum "CX6PM2HBAS72" {
        value 574;
        description
          "CX6PM2HBAS72.";
      }
      enum "CX6PM2HBAS73" {
        value 575;
        description
          "CX6PM2HBAS73.";
      }
      enum "CX6B0BKP0375" {
        value 576;
        description
          "CX6B0BKP0375.";
      }
      enum "CR5B0BKP0392" {
        value 577;
        description
          "CR5B0BKP0392.";
      }
      enum "CX6B0BKP0392" {
        value 578;
        description
          "CX6B0BKP0392.";
      }
      enum "TNRB0BKP0391" {
        value 579;
        description
          "TNRB0BKP0391.";
      }
      enum "CX6P010BKP90" {
        value 580;
        description
          "CX6P010BKP90.";
      }
      enum "CX6B0BKP0394" {
        value 581;
        description
          "CX6B0BKP0394.";
      }
      enum "CR5B0BKP0394" {
        value 582;
        description
          "CR5B0BKP0394.";
      }
      enum "TNRB0BKP0394" {
        value 583;
        description
          "TNRB0BKP0394.";
      }
      enum "CX6D00MPUK10" {
        value 584;
        description
          "CX6D00MPUK10.";
      }
      enum "CR5D00MPUK70" {
        value 585;
        description
          "CR5D00MPUK70.";
      }
      enum "CR2D00MPUE10" {
        value 586;
        description
          "CR2D00MPUE10.";
      }
      enum "TNRD00MPUK70" {
        value 587;
        description
          "TNRD00MPUK70.";
      }
      enum "CX6D0MPUKA90" {
        value 588;
        description
          "CX6D0MPUKA90.";
      }
      enum "CR5D0MPUKA90" {
        value 589;
        description
          "CR5D0MPUKA90.";
      }
      enum "CR2D0MPUEA00" {
        value 590;
        description
          "CR2D0MPUEA00.";
      }
      enum "TNUD0MPUKA90" {
        value 591;
        description
          "TNUD0MPUKA90.";
      }
      enum "CR5D0NPU5070" {
        value 592;
        description
          "CR5D0NPU5070.";
      }
      enum "CX6D0NSU5010" {
        value 593;
        description
          "CX6D0NSU5010.";
      }
      enum "CR2D0NSP5010" {
        value 594;
        description
          "CR2D0NSP5010.";
      }
      enum "CR5DNPU50E70" {
        value 595;
        description
          "CR5DNPU50E70.";
      }
      enum "CR2DNSPE5010" {
        value 596;
        description
          "CR2DNSPE5010.";
      }
      enum "CX6DNPUI120" {
        value 597;
        description
          "CR5D0NPU120.";
      }
      enum "CX6DNSU12010" {
        value 598;
        description
          "CX6DNSU12010.";
      }
      enum "CR5DNPU12070" {
        value 599;
        description
          "CR5DNPU12070.";
      }
      enum "CR2DNSP12010" {
        value 600;
        description
          "CR2DNSP12010.";
      }
      enum "CR5DNPU1207E" {
        value 601;
        description
          "CR5DNPU1207E.";
      }
      enum "CR2DNSP1201E" {
        value 602;
        description
          "CR2DNSP1201E.";
      }
      enum "CX6X0PWRDC70" {
        value 603;
        description
          "CX6X0PWRDC70.";
      }
      enum "CX6M001FBX71" {
        value 604;
        description
          "CX6M001FBX71.";
      }
      enum "CX6M002FBX72" {
        value 605;
        description
          "CX6M002FBX72.";
      }
      enum "CX6M002FBX73" {
        value 606;
        description
          "CX6M002FBX73.";
      }
      enum "fname8090CX600-M8-AC" {
        value 607;
        description
          "CX600-M8-AC chassis.";
      }
      enum "fname8090CX600-M4" {
        value 608;
        description
          "CX600-M4 chassis.";
      }
      enum "fname8090CX600-M16" {
        value 609;
        description
          "CX600-M16 chassis.";
      }
      enum "fname8090CX600-X2-M8-AC" {
        value 610;
        description
          "CX600-X2-M8-AC chassis.";
      }
      enum "fname8090CX600-X1" {
        value 611;
        description
          "CX600-X1 chassis.";
      }
      enum "fname8090CX600-X2" {
        value 612;
        description
          "CX600-X2 chassis.";
      }
      enum "fname8090CX600-X1-M4" {
        value 613;
        description
          "CX600-X1-M4 chassis.";
      }
      enum "fname8090CX600-X2-M16" {
        value 614;
        description
          "CX600-X2-M16 chassis.";
      }
      enum "fname8090NE20E-X1" {
        value 615;
        description
          "NE20E-X1 chassis.";
      }
      enum "fname8090NE20E-X1-M4" {
        value 616;
        description
          "NE20E-X1-M4 chassis.";
      }
      enum "fname8090NE20E-X2" {
        value 617;
        description
          "NE20E-X2 chassis.";
      }
      enum "fname8090NE20E-X2-M8" {
        value 618;
        description
          "NE20E-X2-M8 chassis.";
      }
      enum "fname8031CX600-M2E" {
        value 619;
        description
          "CX600-M2E chassis.";
      }
      enum "fname8031CX600-M2F" {
        value 620;
        description
          "CX600-M2F chassis.";
      }
      enum "fname8090NE20E-X2-M16" {
        value 621;
        description
          "NE20E-X2-M16 chassis.";
      }
      enum "fnameNE20E-S2E" {
        value 622;
        description
          "NE20E-S2E chassis.";
      }
      enum "fnameNE20E-S2F" {
        value 623;
        description
          "NE20E-S2F chassis.";
      }
      enum "fname8090NE40E-X1" {
        value 624;
        description
          "NE40E-X1 chassis.";
      }
      enum "fname8090NE40E-X1-M4" {
        value 625;
        description
          "NE40E-X1-M4 chassis.";
      }
      enum "fname8090NE40E-X2" {
        value 626;
        description
          "NE40E-X2 chassis.";
      }
      enum "fname8090NE40E-M2E" {
        value 627;
        description
          "NE40E-M2E chassis.";
      }
      enum "fname8090NE40E-M2F" {
        value 628;
        description
          "NE40E-M2F chassis.";
      }
      enum "fname8090NE40E-X8" {
        value 629;
        description
          "NE40E-X8 chassis.";
      }
      enum "fname8090NE40E-X16" {
        value 630;
        description
          "NE40E-X16 chassis.";
      }
      enum "fname8090NE40E-X16A" {
        value 631;
        description
          "NE40E-X16A chassis.";
      }
      enum "fname8090NE40E-X16A-HVDC" {
        value 632;
        description
          "NE40E-X16A-HVDC chassis.";
      }
      enum "fname8090NE40E-X8A-HVDC" {
        value 633;
        description
          "NE40E-X8A-HVDC chassis.";
      }
      enum "fnameME60-X16A-HVDC" {
        value 634;
        description
          "ME60-X16A-HVDC chassis.";
      }
      enum "fnameME60-X8A-HVDC" {
        value 635;
        description
          "ME60-X8A-HVDC chassis.";
      }
      enum "fname8090CX600-X16A-HVDC" {
        value 636;
        description
          "CX600-X16A-HVDC chassis.";
      }
      enum "fname8090CX600-X8A-HVDC" {
        value 637;
        description
          "CX600-X8A-HVDC chassis.";
      }
      enum "fnamePTN6900-16A-HVDC" {
        value 638;
        description
          "PTN 6900-16A-HVDC chassis.";
      }
      enum "fnamePTN6900-8A-HVDC" {
        value 639;
        description
          "PTN 6900-8A-HVDC chassis.";
      }
      enum "fname8090CX600-X16A-DO-HVDC" {
        value 640;
        description
          "CX600-X16A-DO-HVDC chassis.";
      }
      enum "fname8090CX600-X8A-DO-HVDC" {
        value 641;
        description
          "CX600-X8A-DO-HVDC chassis.";
      }
      enum "fname8090NE40E-X16A-AC" {
        value 642;
        description
          "NE40E-X16A-AC chassis.";
      }
      enum "fname8090NE40E-X8A-AC" {
        value 643;
        description
          "NE40E-X8A-AC chassis.";
      }
      enum "fnameME60-X16A-AC" {
        value 644;
        description
          "ME60-X16A-AC chassis.";
      }
      enum "fnameME60-X8A-AC" {
        value 645;
        description
          "ME60-X8A-AC chassis.";
      }
      enum "fname8090CX600-X16A-AC" {
        value 646;
        description
          "CX600-X16A-AC chassis.";
      }
      enum "fname8090CX600-X8A-AC" {
        value 647;
        description
          "CX600-X8A-AC chassis.";
      }
      enum "fnamePTN6900-16A-AC" {
        value 648;
        description
          "PTN 6900-16A-AC chassis.";
      }
      enum "fnamePTN6900-8A-AC" {
        value 649;
        description
          "PTN 6900-8A-AC chassis.";
      }
      enum "fname8090CX600-X16A-DO-AC" {
        value 650;
        description
          "CX600-X16A-DO-AC chassis.";
      }
      enum "fname8090CX600-X8A-DO-AC" {
        value 651;
        description
          "CX600-X8A-DO-AC chassis.";
      }
      enum "fname8090NE40E-X16A-DC" {
        value 652;
        description
          "NE40E-X16A-DC chassis.";
      }
      enum "fname8090NE40E-X8A" {
        value 653;
        description
          "NE40E-X8A chassis.";
      }
      enum "fname8090NE40E-X8A-DC" {
        value 654;
        description
          "NE40E-X8A-DC chassis.";
      }
      enum "fname8090NE40E-X2-M8-AC" {
        value 655;
        description
          "NE40E-X2-M8-AC chassis.";
      }
      enum "fname8090NE40E-X2-M16" {
        value 656;
        description
          "NE40E-X2-M16 chassis.";
      }
      enum "fname8090NE20E-S4" {
        value 657;
        description
          "NE20E-S4 chassis.";
      }
      enum "fname8090NE20E-S8-AC" {
        value 658;
        description
          "NE20E-S8-AC chassis.";
      }
      enum "fname8090NE20E-S16" {
        value 659;
        description
          "NE20E-S16 chassis.";
      }
      enum "fname8090PTN6900-1-M4" {
        value 660;
        description
          "PTN 6900-1-M4 Chassis.";
      }
      enum "fname8090PTN6900-2-M8-AC" {
        value 661;
        description
          "PTN 6900-2-M8-AC Chassis.";
      }
      enum "fname8090PTN6900-2-M16" {
        value 662;
        description
          "PTN 6900-2-M16 Chassis.";
      }
      enum "fnamePTN6900-M2E" {
        value 663;
        description
          "PTN 6900-M2E chassis.";
      }
      enum "fnamePTN6900-M2F" {
        value 664;
        description
          "PTN 6900-M2F chassis.";
      }
      enum "fnamePTN6900-M2K" {
        value 665;
        description
          "PTN 6900-M2K chassis.";
      }
      enum "fname8090NE40E-M2H" {
        value 666;
        description
          "NE40E-M2H chassis.";
      }
      enum "fname8031CX600-M2H" {
        value 667;
        description
          "CX600-M2H chassis.";
      }
      enum "fname8031CX600-M2K" {
        value 668;
        description
          "CX600-M2K chassis.";
      }
      enum "fname8090NE40E-M2K" {
        value 669;
        description
          "NE40E-M2K chassis.";
      }
      enum "fname8090CX6602" {
        value 670;
        description
          "CX6602 chassis.";
      }
      enum "fname8031CX600-M2K-DC" {
        value 671;
        description
          "CX600-M2K-DC chassis.";
      }
      enum "fname8031CX600-M2K-B-DC" {
        value 672;
        description
          "CX600-M2K-B-DC chassis.";
      }
      enum "fnamePTN6900-M2K-DC" {
        value 673;
        description
          "PTN6900-M2K-DC chassis.";
      }
      enum "fnamePTN6900-M2K-B-DC" {
        value 674;
        description
          "PTN6900-M2K-B-DC chassis.";
      }
      enum "fname8090CX6602-B-DC" {
        value 675;
        description
          "CX6602-B-DC chassis.";
      }
      enum "fname8090CX6602-DC" {
        value 676;
        description
          "CX6602-DC chassis.";
      }
      enum "fname8090NE40E-M2K-B-DC" {
        value 677;
        description
          "NE40E-M2K-B-DC chassis.";
      }
      enum "fname8090NE40E-M2K-DC" {
        value 678;
        description
          "NE40E-M2K-DC chassis.";
      }
      enum "fnamePTN6900-M2K-AC" {
        value 679;
        description
          "PTN6900-M2K-AC chassis.";
      }
      enum "fname8031CX600-M2K-AC" {
        value 680;
        description
          "CX600-M2K-AC chassis.";
      }
      enum "fname8031CX600-M2K-B-AC" {
        value 681;
        description
          "CX600-M2K-B-AC chassis.";
      }
      enum "fname8090CX6602-AC" {
        value 682;
        description
          "CX6602-AC chassis.";
      }
      enum "fnamePTN6900-M2K-B-AC" {
        value 683;
        description
          "M2K-B-AC chassis.";
      }
      enum "fname8090NE40E-M2K-B-AC" {
        value 684;
        description
          "NE40E-M2K-B-AC chassis.";
      }
      enum "fname8090NE40E-M2K-AC" {
        value 685;
        description
          "NE40E-M2K-AC chassis.";
      }
      enum "fname8090CX6602-B-AC" {
        value 686;
        description
          "CX6602-B-AC chassis.";
      }
      enum "fname8031CX600-M2E-AC" {
        value 687;
        description
          "CX600-M2E-AC chassis.";
      }
      enum "fname8090NE40E-M2E-AC" {
        value 688;
        description
          "NE40E-M2E-AC chassis.";
      }
      enum "fnameNE20E-S2E-AC" {
        value 689;
        description
          "NE20E-S2E-AC chassis.";
      }
      enum "fnamePTN6900-M2E-AC" {
        value 690;
        description
          "PTN6900-M2E-AC chassis.";
      }
      enum "fname8031CX600-M2E-DC" {
        value 691;
        description
          "CX600-M2E-DC chassis.";
      }
      enum "fname8090NE40E-M2E-DC" {
        value 692;
        description
          "NE40E-M2E-DC chassis.";
      }
      enum "fnameNE20E-S2E-DC" {
        value 693;
        description
          "NE20E-S2E-DC chassis.";
      }
      enum "fnamePTN6900-M2E-DC" {
        value 694;
        description
          "PTN6900-M2E-DC chassis.";
      }
      enum "fname8031CX600-M2F-AC" {
        value 695;
        description
          "CX600-M2F-AC chassis.";
      }
      enum "fname8090NE40E-M2F-AC" {
        value 696;
        description
          "NE40E-M2F-AC chassis.";
      }
      enum "fnameNE20E-S2F-AC" {
        value 697;
        description
          "NE20E-S2F-AC chassis.";
      }
      enum "fnamePTN6900-M2F-AC" {
        value 698;
        description
          "PTN6900-M2F-AC chassis.";
      }
      enum "fname8031CX600-M2F-DC" {
        value 699;
        description
          "CX600-M2F-DC chassis.";
      }
      enum "fname8090NE40E-M2F-DC" {
        value 700;
        description
          "NE40E-M2F-DC chassis.";
      }
      enum "fnameNE20E-S2F-DC" {
        value 701;
        description
          "NE20E-S2F-DC chassis.";
      }
      enum "fnamePTN6900-M2F-DC" {
        value 702;
        description
          "PTN6900-M2F-DC chassis.";
      }
      enum "fname8031CX600-M2H-AC" {
        value 703;
        description
          "CX600-M2H-AC chassis.";
      }
      enum "fname8090NE40E-M2H-AC" {
        value 704;
        description
          "NE40E-M2H-AC chassis.";
      }
      enum "fname8031CX600-M2H-DC" {
        value 705;
        description
          "CX600-M2H-DC chassis.";
      }
      enum "fname8090NE40E-M2H-DC" {
        value 706;
        description
          "NE40E-M2H-DC chassis.";
      }
      enum "fname8031CX600-M2K-B" {
        value 707;
        description
          "CX600-M2K-B chassis.";
      }
      enum "fname8090NE40E-M2K-B" {
        value 708;
        description
          "NE40E-M2K-B chassis.";
      }
      enum "fname8090CX6602-B" {
        value 709;
        description
          "CX6602-B chassis.";
      }
      enum "fnamePTN6900-M2K-B" {
        value 710;
        description
          "PTN 6900-M2K-B chassis.";
      }
      enum "fname8031CX600-F1A-14H24Q" {
        value 711;
        description
          "CX600-F1A-14H24Q chassis.";
      }
      enum "fname8090NE40E-F1A-14H24Q" {
        value 712;
        description
          "NE40E-F1A-14H24Q chassis.";
      }
      enum "fname8090CX6601-14H24Q" {
        value 713;
        description
          "CX6601-14H24Q chassis.";
      }
      enum "fnamePTN6900-F1A-14H24Q" {
        value 714;
        description
          "PTN6900-F1A-14H24Q chassis.";
      }
      enum "CX6D00E8GE10" {
        value 715;
        description
          "CX6D00E8GE10.";
      }
      enum "CR5D00E8GE70" {
        value 716;
        description
          "CR5D00E8GE70.";
      }
      enum "CR2D00E8GE11" {
        value 717;
        description
          "CR2D00E8GE11.";
      }
      enum "CX6D00L2XF10" {
        value 718;
        description
          "CX6D00L2XF10.";
      }
      enum "CR5D00L2XF70" {
        value 719;
        description
          "CR5D00L2XF70.";
      }
      enum "CR2D00L2XF11" {
        value 720;
        description
          "CR2D00L2XF11.";
      }
      enum "CX6D00E8GF10" {
        value 721;
        description
          "CX6D00E8GF10.";
      }
      enum "CR5D00E8GF71" {
        value 722;
        description
          "CR5D00E8GF71.";
      }
      enum "CR2D00E8GF11" {
        value 723;
        description
          "CR2D00E8GF11.";
      }
      enum "CX6D000IE170" {
        value 724;
        description
          "CX6D000IE170.";
      }
      enum "CX6D000IE171" {
        value 725;
        description
          "CX6D000IE171.";
      }
      enum "CR56LPUF400A" {
        value 726;
        description
          "CR56LPUF400A.";
      }
      enum "CR56MPUB5" {
        value 727;
        description
          "CR56MPUB5.";
      }
      enum "CR5DLPUFK061" {
        value 728;
        description
          "CR5DLPUFK061.";
      }
      enum "CR5D00LMXF61" {
        value 729;
        description
          "CR5D00LMXF61.";
      }
      enum "CR5D00LAXF60" {
        value 730;
        description
          "CR5D00LAXF60.";
      }
      enum "CR5D0MPUB560" {
        value 731;
        description
          "CR5D0MPUB560.";
      }
      enum "CR5D0MPUC061" {
        value 732;
        description
          "CR5D0MPUC061.";
      }
      enum "CR2D00P4CF11" {
        value 733;
        description
          "CR2D00P4CF11.";
      }
      enum "CX6D00L4XF10" {
        value 734;
        description
          "CX6D00L4XF10.";
      }
      enum "CR5D00L4XF70" {
        value 735;
        description
          "CR5D00L4XF70.";
      }
      enum "CR2D00L4XF10" {
        value 736;
        description
          "CR2D00L4XF10.";
      }
      enum "CX6DL1XE8G10" {
        value 737;
        description
          "CX6DL1XE8G10.";
      }
      enum "CR5DL1XE8G70" {
        value 738;
        description
          "CR5DL1XE8G70.";
      }
      enum "CR2DL1XE8G10" {
        value 739;
        description
          "CR2DL1XE8G10.";
      }
      enum "CR5D00C4CF71" {
        value 740;
        description
          "CR5D00C4CF71.";
      }
      enum "CX6D00C4CF11" {
        value 741;
        description
          "CX6D00C4CF11.";
      }
      enum "CR2D00C4CF11" {
        value 742;
        description
          "CR2D00C4CF11.";
      }
      enum "CR5D000IE170" {
        value 743;
        description
          "CR5D000IE170.";
      }
      enum "CX6D000IE110" {
        value 744;
        description
          "CX6D000IE110.";
      }
      enum "CR2D000IE110" {
        value 745;
        description
          "CR2D000IE110.";
      }
      enum "CR5D000IE171" {
        value 746;
        description
          "CR5D000IE171.";
      }
      enum "CX6D000IE111" {
        value 747;
        description
          "CX6D000IE111.";
      }
      enum "CR2D000IE111" {
        value 748;
        description
          "CR2D000IE111.";
      }
      enum "CR5D000DE170" {
        value 749;
        description
          "CR5D000DE170.";
      }
      enum "CX6D000DE110" {
        value 750;
        description
          "CX6D000DE110.";
      }
      enum "CR2D000DE110" {
        value 751;
        description
          "CR2D000DE110.";
      }
      enum "CR5D000DE171" {
        value 752;
        description
          "CR5D000DE171.";
      }
      enum "CX6D000DE111" {
        value 753;
        description
          "CX6D000DE111.";
      }
      enum "CR2D000DE111" {
        value 754;
        description
          "CR2D000DE111.";
      }
      enum "CR5DSFU0K06B" {
        value 755;
        description
          "CR5DSFU0K06B.";
      }
      enum "CR5D00C4T370" {
        value 756;
        description
          "CR5D00C4T370.";
      }
      enum "CR57EFGFB" {
        value 757;
        description
          "CR57EFGFB.";
      }
      enum "CR57EFGFB2" {
        value 758;
        description
          "CR57EFGFB2.";
      }
      enum "CR57LBXF" {
        value 759;
        description
          "CR57LBXF.";
      }
      enum "CR57LBXF2" {
        value 760;
        description
          "CR57LBXF2.";
      }
      enum "CR57E1NCB2" {
        value 761;
        description
          "CR57E1NCB2.";
      }
      enum "CR9D00EANB83" {
        value 762;
        description
          "CR9D00EANB83.";
      }
      enum "CR9D00D8NC81" {
        value 763;
        description
          "CR9D00D8NC81.";
      }
     enum "CR57EBGFD0" {
        value 764;
        description
          "CR57EBGFD0.";
      }
      enum "CR58E4KE4NA0" {
        value 765;
        description
          "CR58E4KE4NA0.";
      }
      enum "CR57E1MCB" {
        value 766;
        description
          "CR57E1MCB.";
      }
      enum "CR57E1MCB2" {
        value 767;
        description
          "CR57E1MCB2.";
      }
      enum "CR57L6XF" {
        value 768;
        description
          "CR57L6XF.";
      }
      enum "CR57L6XF0" {
        value 769;
        description
          "CR57L6XF0.";
      }
      enum "CR57P8UF" {
        value 770;
        description
          "CR57P8UF.";
      }
      enum "CR5D0P8UF70" {
        value 771;
        description
          "CR5D0P8UF70.";
      }
      enum "CR5D00LBXF72" {
        value 772;
        description
          "CR5D00LBXF72.";
      }
      enum "CR5D0L6XFA70" {
        value 773;
        description
          "CR5D0L6XFA70.";
      }
      enum "CR5D00E1NC75" {
        value 774;
        description
          "CR5D00E1NC75.";
      }
      enum "CR5D0EFGFA71" {
        value 775;
        description
          "CR5D0EFGFA71.";
      }
      enum "CR5D00E1MC70" {
        value 776;
        description
          "CR5D00E1MC70.";
      }
      enum "CR5D00P8UF70" {
        value 777;
        description
          "CR5D00P8UF70.";
      }
      enum "CR5D00E1NC74" {
        value 778;
        description
          "CR5D00E1NC74.";
      }
      enum "CR5D00LBXF71" {
        value 779;
        description
          "CR5D00LBXF71.";
      }
      enum "CR57LPUF480B" {
        value 780;
        description
          "CR57LPUF480B.";
      }
      enum "CR57FRA200A" {
        value 781;
        description
          "CR57FRA200A.";
      }
      enum "CR57LPUF120A" {
        value 782;
        description
          "CR57LPUF120A.";
      }
      enum "CR57LPUF240A" {
        value 783;
        description
          "CR57LPUF240A.";
      }
      enum "CR57SRU200A" {
        value 784;
        description
          "CR57SRU200A.";
      }
      enum "CR57SFU200C" {
        value 785;
        description
          "CR57SFU200C.";
      }
      enum "CR57SFU200B" {
        value 786;
        description
          "CR57SFU200B.";
      }
      enum "CR5DLPUFB070" {
        value 787;
        description
          "CR5DLPUFB070.";
      }
      enum "CR5DLPUFB07B" {
        value 788;
        description
          "CR5DLPUFB07B.";
      }
      enum "CR5DLPUFF070" {
        value 789;
        description
          "CR5DLPUFF070.";
      }
      enum "CR5DLPUFF080" {
        value 790;
        description
          "CR5DLPUFF080.";
      }
      enum "CR5DLPUFF07B" {
        value 791;
        description
          "CR5DLPUFF07B.";
      }
      enum "CR5DSFUIE07B" {
        value 792;
        description
          "CR5DSFUIE07B.";
      }
      enum "CR5DSFUIE07D" {
        value 793;
        description
          "CR5DSFUIE07D.";
      }
      enum "CR5D0MPUB570" {
        value 794;
        description
          "CR5D0MPUB570.";
      }
      enum "CX6D0MPUB570" {
        value 795;
        description
          "CX6D0MPUB570.";
      }
      enum "CR5D0SRUA970" {
        value 796;
        description
          "CR5D0SRUA970.";
      }
      enum "CR5D0SRUA870" {
        value 797;
        description
          "CR5D0SRUA870.";
      }
      enum "CX6D0SRUA970" {
        value 798;
        description
          "CX6D0SRUA970.";
      }
      enum "CX6D0SRUA870" {
        value 799;
        description
          "CX6D0SRUA870.";
      }
      enum "CR5D00E8NC70" {
        value 800;
        description
          "CR5D00E8NC70.";
      }
      enum "CR5D00E8NC7B" {
        value 801;
        description
          "CR5D00E8NC7B.";
      }
      enum "CR5DLPUF517E" {
        value 802;
        description
          "CR5DLPUF517E.";
      }
      enum "CR5D0EMGFA7J" {
        value 803;
        description
          "CR5D0EMGFA7J.";
      }
      enum "CR5DL2XEFG7J" {
        value 804;
        description
          "CR5DL2XEFG7J.";
      }
      enum "CR5DSFUIU07C" {
        value 805;
        description
          "CR5DSFUIU07C.";
      }
      enum "CR5DSFUIM07C" {
        value 806;
        description
          "CR5DSFUIM07C.";
      }
      enum "CX6DSFUIU07C" {
        value 807;
        description
          "CX6DSFUIU07C.";
      }
      enum "CX6DSFUIM07C" {
        value 808;
        description
          "CX6DSFUIM07C.";
      }
      enum "CR5DSFUIU07B" {
        value 809;
        description
          "CR5DSFUIU07B.";
      }
      enum "CR5DSFUIM07B" {
        value 810;
        description
          "CR5DSFUIM07B.";
      }
      enum "CX6DSFUIU07B" {
        value 811;
        description
          "CX6DSFUIU07B.";
      }
      enum "CX6DSFUIM07B" {
        value 812;
        description
          "CX6DSFUIM07B.";
      }
      enum "CR57FRA1TA" {
        value 813;
        description
          "CR57FRA1TA.";
      }
      enum "CR5D0LBXFA70" {
        value 814;
        description
          "CR5D0LBXFA70.";
      }
      enum "CR5D0E2MCA70" {
        value 815;
        description
          "CR5D0E2MCA70.";
      }
      enum "CR5D00E1NC76" {
        value 816;
        description
          "CR5D00E1NC76.";
      }
      enum "CR5D00E1NC78" {
        value 817;
        description
          "CR5D00E1NC78.";
      }
      enum "CR5D00E1ND71" {
        value 818;
        description
          "CR5D00E1ND71.";
      }
      enum "CR5D00E1ND72" {
        value 819;
        description
          "CR5D00E1ND72.";
      }
      enum "CR5D0LBXFA7B" {
        value 820;
        description
          "CR5D0LBXFA7B.";
      }
      enum "CR5D0E2MCA7B" {
        value 821;
        description
          "CR5D0E2MCA7B.";
      }
      enum "CR5D00E1NC7B" {
        value 822;
        description
          "CR5D00E1NC7B.";
      }
      enum "CR5D00E1NC7C" {
        value 823;
        description
          "CR5D00E1NC7C.";
      }
      enum "CR5D00E2NC70" {
        value 824;
        description
          "CR5D00E2NC70.";
      }
      enum "CR5D00E2NC71" {
        value 825;
        description
          "CR5D00E2NC71.";
      }
      enum "CR5DL6XE8G70" {
        value 826;
        description
          "CR5DL6XE8G70.";
      }
      enum "ME0DL6XE8G70" {
        value 827;
        description
          "ME0DL6XE8G70.";
      }
      enum "CR5D00E2ND70" {
        value 828;
        description
          "CR5D00E2ND70.";
      }
      enum "CR5DE1NLBX72" {
        value 829;
        description
          "CR5DE1NLBX72.";
      }
      enum "CR5D00E2ND71" {
        value 830;
        description
          "CR5D00E2ND71.";
      }
      enum "CR5DE1NLBX73" {
        value 831;
        description
          "CR5DE1NLBX73.";
      }
      enum "ME0D0E2NBB70" {
        value 832;
        description
          "ME0D0E2NBB70.";
      }
      enum "CR5D00LFXF70" {
        value 833;
        description
          "CR5D00LFXF70.";
      }
      enum "CR5DE2NLBX70" {
        value 834;
        description
          "CR5DE2NLBX70.";
      }
      enum "CR5DE1NLBX70" {
        value 835;
        description
          "CR5DE1NLBX70.";
      }
      enum "CR5D00E2NC73" {
        value 836;
        description
          "CR5D00E2NC73.";
      }
      enum "CR5D00E2NC74" {
        value 837;
        description
          "CR5D00E2NC74.";
      }
      enum "CR5D00LFXF73" {
        value 838;
        description
          "CR5D00LFXF73.";
      }
      enum "CR5DE2NLBX73" {
        value 839;
        description
          "CR5DE2NLBX73.";
      }
      enum "CR5DE1NLBX71" {
        value 840;
        description
          "CR5DE1NLBX71.";
      }
      enum "CR5DSFUIE07C" {
        value 841;
        description
          "CR5DSFUIE07C.";
      }
      enum "CX6DSFUIE01C" {
        value 842;
        description
          "CX6DSFUIE01C.";
      }
      enum "CR5D0SRUA570" {
        value 843;
        description
          "CR5D0SRUA570.";
      }
      enum "CX6D0SRUA510" {
        value 844;
        description
          "CX6D0SRUA510.";
      }
      enum "CX6DSFUIE01B" {
        value 845;
        description
          "CX6DSFUIE01B.";
      }
      enum "CR5D0MPUB460" {
        value 846;
        description
          "CR5D0MPUB460.";
      }
      enum "CX6D0MPUB410" {
        value 847;
        description
          "CX6D0MPUB410.";
      }
      enum "CR5DLPUFM070" {
        value 848;
        description
          "CR5DLPUFM070.";
      }
      enum "CR5D00LMXF70" {
        value 849;
        description
          "CR5D00LMXF70.";
      }
      enum "CR5DE2NLFX70" {
        value 850;
        description
          "CR5DE2NLFX70.";
      }
      enum "CR5D0SRUA872" {
        value 851;
        description
          "CR5D0SRUA872.";
      }
      enum "CR5DSFUIM17C" {
        value 852;
        description
          "CR5DSFUIM17C.";
      }
      enum "CR5DSFUIM17B" {
        value 853;
        description
          "CR5DSFUIM17B.";
      }
      enum "CX6DSFUIM17B" {
        value 854;
        description
          "CX6DSFUIM17B.";
      }
      enum "CX6DSFUIT27B" {
        value 855;
        description
          "CX6DSFUIT27B.";
      }
      enum "CX6D0SRUA872" {
        value 856;
        description
          "CX6D0SRUA872.";
      }
      enum "CX6DSFUIM17C" {
        value 857;
        description
          "CX6DSFUIM17C.";
      }
      enum "TNRDSFUIM17B" {
        value 858;
        description
          "TNRDSFUIM17B.";
      }
      enum "TNRDSFUIT27B" {
        value 859;
        description
          "TNRDSFUIT27B.";
      }
      enum "TNRD0SRUA872" {
        value 860;
        description
          "TNRD0SRUA872.";
      }
      enum "TNRDSFUIM17C" {
        value 861;
        description
          "TNRDSFUIM17C.";
      }
      enum "CX6DSFUIM11B" {
        value 862;
        description
          "CX6DSFUIM11B.";
      }
      enum "CX6D0SRUA812" {
        value 863;
        description
          "CX6D0SRUA812.";
      }
      enum "CX6DSFUIM11C" {
        value 864;
        description
          "CX6DSFUIM11C.";
      }
      enum "ME0DSFUIM17B" {
        value 865;
        description
          "ME0DSFUIM17B.";
      }
      enum "ME0D0SRUA872" {
        value 866;
        description
          "ME0D0SRUA872.";
      }
      enum "ME0DSFUIM17C" {
        value 867;
        description
          "ME0DSFUIM17C.";
      }
      enum "CR5D0SRUAA70" {
        value 868;
        description
          "CR5D0SRUAA70.";
      }
      enum "CR5DSFUIU07D" {
        value 869;
        description
          "CR5DSFUIU07D.";
      }
      enum "CR5DSFUIT27E" {
        value 870;
        description
          "CR5DSFUIT27E.";
      }
      enum "CR5DSFUIU07F" {
        value 871;
        description
          "CR5DSFUIU07F.";
      }
      enum "CX6DSFUIU07F" {
        value 872;
        description
          "CX6DSFUIU07F.";
      }
      enum "CX6DSFUIT27E" {
        value 873;
        description
          "CX6DSFUIT27E.";
      }
      enum "TNRDSFUIU07F" {
        value 874;
        description
          "TNRDSFUIU07F.";
      }
      enum "TNRDSFUIT27E" {
        value 875;
        description
          "TNRDSFUIT27E.";
      }
      enum "CX6D0SRUAA70" {
        value 876;
        description
          "CX6D0SRUAA70.";
      }
      enum "CX6DSFUIU07D" {
        value 877;
        description
          "CX6DSFUIU07D.";
      }
      enum "TNRD0SRUAA70" {
        value 878;
        description
          "TNRD0SRUAA70.";
      }
      enum "TNRDSFUIU07D" {
        value 879;
        description
          "TNRDSFUIU07D.";
      }
      enum "CR5D00E4NC70" {
        value 880;
        description
          "CR5D00E4NC70.";
      }
      enum "CR5D00D4NC70" {
        value 881;
        description
          "CR5D00D4NC70.";
      }
      enum "CR5D00D8NC70" {
        value 882;
        description
          "CR5D00D8NC70.";
      }
      enum "CR5D00EENB70" {
        value 883;
        description
          "CR5D00EENB70.";
      }
      enum "ANKD001EV106" {
        value 884;
        description
          "ANKD001EV106.";
      }
      enum "CR5D00EENB7B" {
        value 885;
        description
          "CR5D00EENB7B.";
      }
      enum "CR5D00EENB7P" {
        value 886;
        description
          "CR5D00EENB7P.";
      }
      enum "CR5DLPUFME70" {
        value 887;
        description
          "CR5DLPUFME70.";
      }
      enum "CR5D00E4NC7P" {
        value 888;
        description
          "CR5D00E4NC7P.";
      }
      enum "ME0DBSUFM070" {
        value 889;
        description
          "ME0DBSUFM070.";
      }
      enum "ME0DMSUFM070" {
        value 890;
        description
          "ME0DMSUFM070.";
      }
      enum "CR5DE2NLFX71" {
        value 891;
        description
          "CR5DE2NLFX71.";
      }
      enum "CR5DLPUFF17E" {
        value 892;
        description
          "CR5DLPUFF17E.";
      }
      enum "CR5DLPUFF17Q" {
        value 893;
        description
          "CR5DLPUFF17Q.";
      }
      enum "ME0DBSUFF073" {
        value 894;
        description
          "ME0DBSUFF073.";
      }
      enum "ME0DBSUFF072" {
        value 895;
        description
          "ME0DBSUFF072.";
      }
      enum "CR5DE2NLFX72" {
        value 896;
        description
          "CR5DE2NLFX72.";
      }
      enum "CR5DE2NLFX73" {
        value 897;
        description
          "CR5DE2NLFX73.";
      }
      enum "CR5D00E4NB70" {
        value 898;
        description
          "CR5D00E4NB70.";
      }
      enum "CR5D00E4NB7B" {
        value 899;
        description
          "CR5D00E4NB7B.";
      }
      enum "CR5D00E4NB7C" {
        value 900;
        description
          "CR5D00E4NB7C.";
      }
      enum "ME0DE2NLEX7C" {
        value 901;
        description
          "ME0DE2NLEX7C.";
      }
      enum "ME0D0E4NBM70" {
        value 902;
        description
          "ME0D0E4NBM70.";
      }
      enum "fname8090CX600-X8" {
        value 903;
        description
          "CX600-X8 chassis.";
      }
      enum "fname8090CX600-X8A" {
        value 904;
        description
          "CX600-X8A chassis.";
      }
      enum "fname8090CX600-X8A-DC" {
        value 905;
        description
          "CX600-X8A-DC chassis.";
      }
      enum "fname8090CX600-X16" {
        value 906;
        description
          "CX600-X16 chassis.";
      }
      enum "fname8090CX600-X16A" {
        value 907;
        description
          "CX600-X16A chassis.";
      }
      enum "fname8090CX600-X16A-DC" {
        value 908;
        description
          "CX600-X16A-DC chassis.";
      }
      enum "fnamePTN6900TNRK003BKP01" {
        value 909;
        description
          "PTN 6900-3 chassis.";
      }
      enum "fnamePTN6900TNRZ1BKPE" {
        value 910;
        description
          "PTN 6900-3-DC chassis.";
      }
      enum "fname8031CX6003AC" {
        value 911;
        description
          "CX600-X3 chassis.";
      }
      enum "fname8031CX6003DCDO" {
        value 912;
        description
          "CX600-X3-DC-DO chassis.";
      }
      enum "fname8031CX6003ACDO" {
        value 913;
        description
          "CX600-X3-AC-DO chassis.";
      }
      enum "fname8031CX600X8DO" {
        value 914;
        description
          "CX600-X8-DO chassis.";
      }
      enum "fname8031CX6003DC" {
        value 915;
        description
          "CX600-X3-DC chassis.";
      }
      enum "fname8090NE40E3AC" {
        value 916;
        description
          "NE40E-X3 chassis.";
      }
      enum "fname8090NE40E3DC" {
        value 917;
        description
          "NE40E-X3-DC chassis.";
      }
      enum "fnameME60-X3-AC" {
        value 918;
        description
          "ME60-X3 chassis.";
      }
      enum "fnameME60-X3-DC" {
        value 919;
        description
          "ME60-X3-DC chassis.";
      }
      enum "fnamePTN6900-3A" {
        value 920;
        description
          "PTN 6900-3A chassis.";
      }
      enum "fnameME60-X3A" {
        value 921;
        description
          "ME60-X3A chassis.";
      }
      enum "fname8090NE40E-X3A" {
        value 922;
        description
          "NE40E-X3A chassis.";
      }
      enum "fname8031CX600-X3A" {
        value 923;
        description
          "CX600-X3A chassis.";
      }
      enum "fnameME60-X8" {
        value 924;
        description
          "ME60-X8 chassis.";
      }
      enum "fnameME60-X16" {
        value 925;
        description
          "ME60-X16 chassis.";
      }
      enum "fnameME60-X8A" {
        value 926;
        description
          "ME60-X8A chassis.";
      }
      enum "fnameME60-X8A-DC" {
        value 927;
        description
          "ME60-X8A-DC chassis.";
      }
      enum "fnameME60-X16A" {
        value 928;
        description
          "ME60-X16A chassis.";
      }
      enum "fnameME60-X16A-DC" {
        value 929;
        description
          "ME60-X16A-DC chassis.";
      }
      enum "fnamePTN6900Half" {
        value 930;
        description
          "PTN 6900-8 chassis.";
      }
      enum "fnamePTN6900Whole" {
        value 931;
        description
          "PTN 6900-16 chassis.";
      }
      enum "fnamePTN6900-8A" {
        value 932;
        description
          "PTN 6900-8A chassis.";
      }
      enum "fnamePTN6900-8A-DC" {
        value 933;
        description
          "PTN 6900-8A-DC chassis.";
      }
      enum "fnamePTN6900-16A" {
        value 934;
        description
          "PTN 6900-16A chassis.";
      }
      enum "fnamePTN6900-16A-DC" {
        value 935;
        description
          "PTN 6900-16A-DC chassis.";
      }
      enum "fname8090CX600-X8A-DO" {
        value 936;
        description
          "CX600-X8A-DO chassis.";
      }
      enum "fname8090CX600-X8A-DO-DC" {
        value 937;
        description
          "CX600-X8A-DO-DC chassis.";
      }
      enum "fname8090CX600-X16A-DO" {
        value 938;
        description
          "CX600-X16A-DO chassis.";
      }
      enum "fname8090CX600-X16A-DO-DC" {
        value 939;
        description
          "CX600-X16A-DO-DC chassis.";
      }
      enum "fname8090CX600-X16-DO" {
        value 940;
        description
          "CX600-X16-DO chassis.";
      }
      enum "fname8031CX600-X3A-DO" {
        value 941;
        description
          "CX600-X3A-DO chassis.";
      }
      enum "fname8090CX600-X2-M8A-AC" {
        value 942;
        description
          "CX600-X2-M8A-AC chassis.";
      }
      enum "fname8090CX600-X2-M8A-DC" {
        value 943;
        description
          "CX600-X2-M8A-DC chassis.";
      }
      enum "fname8031CX600-M8ADO" {
        value 944;
        description
          "CX600-M8ADO chassis.";
      }
      enum "fname8031CX600-M8ADO-DC" {
        value 945;
        description
          "CX600-M8ADO-DC chassis.";
      }
      enum "fname8090NE20E-S8A-AC" {
        value 946;
        description
          "NE20E-S8A-AC chassis.";
      }
      enum "fname8090NE20E-S8A-DC" {
        value 947;
        description
          "NE20E-S8A-DC chassis.";
      }
      enum "fname8090NE40E-X2-M8A-AC" {
        value 948;
        description
          "NE40E-X2-M8A-AC chassis.";
      }
      enum "fname8090NE40E-X2-M8A-DC" {
        value 949;
        description
          "NE40E-X2-M8A-DC chassis.";
      }
      enum "fname8090PTN6900-2-M8A-AC" {
        value 950;
        description
          "PTN 6900-2-M8A-AC chassis.";
      }
      enum "fname8090PTN6900-2-M8A-DC" {
        value 951;
        description
          "PTN 6900-2-M8A-DC chassis.";
      }
      enum "fnameME60-X2-M8A-AC" {
        value 952;
        description
          "ME60-X2-M8A-AC chassis.";
      }
      enum "fnameME60-X2-M8A-DC" {
        value 953;
        description
          "ME60-X2-M8A-DC chassis.";
      }
      enum "fname8090CX600-X2-M16A" {
        value 954;
        description
          "CX600-X2-M16A chassis.";
      }
      enum "fname8031CX600-M16ADO" {
        value 955;
        description
          "CX600-M16ADO chassis.";
      }
      enum "fname8090CX600-X2-M16B" {
        value 956;
        description
          "CX600-X2-M16B chassis.";
      }
      enum "fname8090NE20E-S16A" {
        value 957;
        description
          "NE20E-S16A chassis.";
      }
      enum "fname8090NE20E-S16B" {
        value 958;
        description
          "NE20E-S16B chassis.";
      }
      enum "fname8090NE40E-X2-M16A" {
        value 959;
        description
          "NE40E-X2-M16A chassis.";
      }
      enum "fname8090NE40E-X2-M16B" {
        value 960;
        description
          "NE40E-X2-M16B chassis.";
      }
      enum "fname8090PTN6900-2-M16A" {
        value 961;
        description
          "PTN 6900-2-M16A chassis.";
      }
      enum "fname8090PTN6900-2-M16B" {
        value 962;
        description
          "PTN 6900-2-M16B chassis.";
      }
      enum "fnameME60-X2-M16A" {
        value 963;
        description
          "ME60-X2-M16A chassis.";
      }
      enum "fname8090CX600-M8-DC" {
        value 964;
        description
          "CX600-M8-DC chassis.";
      }
      enum "fname8090CX600-X2-M8-DC" {
        value 965;
        description
          "CX600-X2-M8-DC chassis.";
      }
      enum "fname8090CX600-M8A-DC" {
        value 966;
        description
          "CX600-X2-M8A-DC chassis.";
      }
      enum "fname8090CX600-M8A-AC" {
        value 967;
        description
          "CX600-X2-M8A-AC chassis.";
      }
      enum "fname8090NE40E-X2-M8-DC" {
        value 968;
        description
          "NE40E-X2-M8-DC chassis.";
      }
      enum "fname8090NE20E-S8-DC" {
        value 969;
        description
          "NE20E-S8-DC chassis.";
      }
      enum "fname8090PTN6900-2-M8-DC" {
        value 970;
        description
          "PTN 6900-2-M8-DC Chassis.";
      }
      enum "fnameME60-X2-M8-AC" {
        value 971;
        description
          "ME60-X2-M8-AC chassis.";
      }
      enum "fnameME60-X2-M8-DC" {
        value 972;
        description
          "ME60-X2-M8-DC chassis.";
      }
      enum "fnameME60-X2-M16" {
        value 973;
        description
          "ME60-X2-M16 chassis.";
      }
      enum "CR5DSFUIT060" {
        value 974;
        description
          "CR5DSFUIT060.";
      }
      enum "CR5DSFUIT06E" {
        value 975;
        description
          "CR5DSFUIT06E.";
      }
      enum "CR5DSFUIT26A" {
        value 976;
        description
          "CR5DSFUIT26A.";
      }
      enum "CR5DSFUIT16E" {
        value 977;
        description
          "CR5DSFUIT16E.";
      }
      enum "CR5DE8NEDX61" {
        value 978;
        description
          "CR5DE8NEDX61.";
      }
      enum "CR5D00E8NC61" {
        value 979;
        description
          "CR5D00E8NC61.";
      }
      enum "CR5D00E8NC80" {
        value 980;
        description
          "CR5D00E8NC80.";
      }
      enum "CR5D00EDNB60" {
        value 981;
        description
          "CR5D00EDNB60.";
      }
      enum "CR5D00EDNB61" {
        value 982;
        description
          "CR5D00EDNB61.";
      }
      enum "CR5DEDNLIX60" {
        value 983;
        description
          "CR5DEDNLIX60.";
      }
      enum "CR5DLPUFT060" {
        value 984;
        description
          "CR5DLPUFT060.";
      }
      enum "CR56SFU1TA" {
        value 985;
        description
          "CR56SFU1TA.";
      }
      enum "CR5D00EFMB60" {
        value 986;
        description
          "CR5D00EFMB60.";
      }
      enum "CR5D00E8NC60" {
        value 987;
        description
          "CR5D00E8NC60.";
      }
      enum "CR56LPU1TB" {
        value 988;
        description
          "CR56LPU1TB.";
      }
      enum "CR56E8NC" {
        value 989;
        description
          "CR56E8NC.";
      }
      enum "CR56EFMB" {
        value 990;
        description
          "CR56EFMB.";
      }
      enum "CR50OFC400C" {
        value 991;
        description
          "CR50OFC400C.";
      }
      enum "fname8090NE5000E-X8" {
        value 992;
        description
          "NE5000EX8 Chassis.";
      }
      enum "fname8090NE5000E-20" {
        value 993;
        description
          "NE5000E-20 Chassis.";
      }
      enum "fname8090NE9000-20" {
        value 994;
        description
          "NE9000-20 Chassis.";
      }
      enum "fname8090NE9000-8" {
        value 995;
        description
          "NE9000-8 Chassis.";
      }
      enum "CR5D0SRUB060" {
        value 996;
        description
          "CR5D0SRUB060.";
      }
      enum "CR56SRUB1TA" {
        value 997;
        description
          "CR56SRUB1TA.";
      }
      enum "CR5D0SFUT061" {
        value 998;
        description
          "CR5D0SFUT061.";
      }
      enum "CR56SFU1TC" {
        value 999;
        description
          "CR56SFU1TC.";
      }
      enum "CR56FRA1TA" {
        value 1000;
        description
          "CR56FRA1TA.";
      }
      enum "CR5D00LFXF74" {
        value 1001;
        description
          "CR5D00LFXF74.";
      }
      enum "CR5D00E2NC72" {
        value 1002;
        description
          "CR5D00E2NC72.";
      }
      enum "CR57LFXFE1" {
        value 1003;
        description
          "CR57LFXFE1.";
      }
      enum "CR57E2NCE1" {
        value 1004;
        description
          "CR57E2NCE1.";
      }
      enum "CR57L2XFB" {
        value 1005;
        description
          "CR57L2XFB.";
      }
      enum "CR5D0L2XFA71" {
        value 1006;
        description
          "CR5D0L2XFA71.";
      }
      enum "CR5D0EFGFA70" {
        value 1007;
        description
          "CR5D0EFGFA70.";
      }
      enum "CR5D00N2NC61" {
        value 1008;
        description
          "CR5D00N2NC61.";
      }
      enum "CR5D00E1NC62" {
        value 1009;
        description
          "CR5D00E1NC62.";
      }
      enum "CR57L2XFC2" {
        value 1010;
        description
          "CR57L2XFC2.";
      }
      enum "CR5DNPU24070" {
        value 1011;
        description
          "CR5DNPU24070.";
      }
      enum "CR5DNPU24071" {
        value 1012;
        description
          "CR5DNPU24071.";
      }
      enum "CR5DNPU1TM70" {
        value 1013;
        description
          "CR5DNPU1TM70.";
      }
      enum "CR5DNPU1TM71" {
        value 1014;
        description
          "CR5DNPU1TM71.";
      }
      enum "CX6DNPU1TM70" {
        value 1015;
        description
          "CX6DNPU1TM70.";
      }
      enum "CR2DNSPD0010" {
        value 1016;
        description
          "CR2DNSPD0010.";
      }
      enum "CR2DNSPA0010" {
        value 1017;
        description
          "CR2DNSPA0010.";
      }
      enum "CR2DNSPB0010" {
        value 1018;
        description
          "CR2DNSPB0010.";
      }
      enum "CR5DNPU48070" {
        value 1019;
        description
          "CR5DNPU48070.";
      }
      enum "CR2DNSPC0010" {
        value 1020;
        description
          "CR2DNSPC0010.";
      }
      enum "CX6D00MPUK11" {
        value 1021;
        description
          "CX6D00MPUK11.";
      }
      enum "CX6D0MPUK170" {
        value 1022;
        description
          "CX6D0MPUK170.";
      }
      enum "ME0D0MPUK171" {
        value 1023;
        description
          "ME0D0MPUK171.";
      }
      enum "CR5D0MPUK170" {
        value 1024;
        description
          "CR5D0MPUK170.";
      }
      enum "TNUD00MPUK71" {
        value 1025;
        description
          "TNUD00MPUK71.";
      }
      enum "CR2D0MPUE110" {
        value 1026;
        description
          "CR2D0MPUE110.";
      }
      enum "CR2DP4C2HF11" {
        value 1027;
        description
          "CR2DP4C2HF11.";
      }
      enum "CR5DP4C2HF70" {
        value 1028;
        description
          "CR5DP4C2HF70.";
      }
      enum "CR2DP2C1HF11" {
        value 1029;
        description
          "CR2DP2C1HF11.";
      }
      enum "CR5DP2C1HF70" {
        value 1030;
        description
          "CR5DP2C1HF70.";
      }
      enum "CR5DLPUF5070" {
        value 1031;
        description
          "CR5DLPUF5070.";
      }
      enum "CR5DLPUF5170" {
        value 1032;
        description
          "CR5DLPUF5170.";
      }
      enum "CR5DLPUF517B" {
        value 1033;
        description
          "CR5DLPUF517B.";
      }
      enum "CR5D0L5XFA71" {
        value 1034;
        description
          "CR5D0L5XFA71.";
      }
      enum "CR5D0L4XFA70" {
        value 1035;
        description
          "CR5D0L4XFA70.";
      }
      enum "CR5D0EMGFA70" {
        value 1036;
        description
          "CR5D0EMGFA70.";
      }
      enum "CR5DL2XEFG7A" {
        value 1037;
        description
          "CR5DL2XEFG7A.";
      }
      enum "CR5DL3XEFG7C" {
        value 1038;
        description
          "CR5DL3XEFG7C.";
      }
      enum "CR5D0L5XFA7B" {
        value 1039;
        description
          "CR5D0L5XFA7B.";
      }
      enum "CR5D0L4XFA7B" {
        value 1040;
        description
          "CR5D0L4XFA7B.";
      }
      enum "CR5D0EMGFA7B" {
        value 1041;
        description
          "CR5D0EMGFA7B.";
      }
      enum "CR5DL2XEFG7B" {
        value 1042;
        description
          "CR5DL2XEFG7B.";
      }
      enum "CR5D00L5XF72" {
        value 1043;
        description
          "CR5D00L5XF72.";
      }
      enum "CR5D00EMGF73" {
        value 1044;
        description
          "CR5D00EMGF73.";
      }
      enum "CR5DL2XEFG72" {
        value 1045;
        description
          "CR5DL2XEFG72.";
      }
      enum "CR5D0L5XFA7L" {
        value 1046;
        description
          "CR5D0L5XFA7L.";
      }
      enum "CR5DL2XEIG7L" {
        value 1047;
        description
          "CR5DL2XEIG7L.";
      }
      enum "CR5D0EMGFA7L" {
        value 1048;
        description
          "CR5D0EMGFA7L.";
      }
      enum "CR5DLPUFA071" {
        value 1049;
        description
          "CR5DLPUFA071.";
      }
      enum "CR5DLPUFA07B" {
        value 1050;
        description
          "CR5DLPUFA07B.";
      }
      enum "CR5D00E2MC70" {
        value 1051;
        description
          "CR5D00E2MC70.";
      }
      enum "CR5D0LAXFA71" {
        value 1052;
        description
          "CR5D0LAXFA71.";
      }
      enum "CR5D00E1NC72" {
        value 1053;
        description
          "CR5D00E1NC72.";
      }
      enum "CR5D00E2MC7B" {
        value 1054;
        description
          "CR5D00E2MC7B.";
      }
      enum "CR5D0LAXFA7B" {
        value 1055;
        description
          "CR5D0LAXFA7B.";
      }
      enum "CR5D00E2MC71" {
        value 1056;
        description
          "CR5D00E2MC71.";
      }
      enum "CR5D0LAXFA72" {
        value 1057;
        description
          "CR5D0LAXFA72.";
      }
      enum "CR5D00E1NC73" {
        value 1058;
        description
          "CR5D00E1NC73.";
      }
      enum "ME0DBSUFA070" {
        value 1059;
        description
          "ME0DBSUFA070.";
      }
      enum "ME0DBSUFF070" {
        value 1060;
        description
          "ME0DBSUFF070.";
      }
      enum "CR5DLPUFB07E" {
        value 1061;
        description
          "CR5DLPUFB07E.";
      }
      enum "CR5DLPUFF07E" {
        value 1062;
        description
          "CR5DLPUFF07E.";
      }
      enum "ME0DMSUFA070" {
        value 1063;
        description
          "ME0DMSUFA070.";
      }
      enum "ME0DMSUF5170" {
        value 1064;
        description
          "ME0DMSUF5170.";
      }
      enum "ME0DBSUF5170" {
        value 1065;
        description
          "ME0DBSUF5170.";
      }
      enum "CR5DLPUF507L" {
        value 1066;
        description
          "CR5DLPUF507L.";
      }
      enum "CR5DL4XEBG7L" {
        value 1067;
        description
          "CR5DL4XEBG7L.";
      }
      enum "CR5D0L5XFA7J" {
        value 1068;
        description
          "CR5D0L5XFA7J.";
      }
      enum "CR5D00LBXF7L" {
        value 1069;
        description
          "CR5D00LBXF7L.";
      }
      enum "CR5D00L5XF73" {
        value 1070;
        description
          "CR5D00L5XF73.";
      }
      enum "CR5D00EMGF74" {
        value 1071;
        description
          "CR5D00EMGF74.";
      }
      enum "CR5DL2XEFG73" {
        value 1072;
        description
          "CR5DL2XEFG73.";
      }
      enum "CR5DLPUFA07J" {
        value 1073;
        description
          "CR5DLPUFA07J.";
      }
      enum "CR5DLPUFA27E" {
        value 1074;
        description
          "CR5DLPUFA27E.";
      }
      enum "CR5D00LFXF7L" {
        value 1075;
        description
          "CR5D00LFXF7L.";
      }
      enum "CR5D00TBXF71" {
        value 1076;
        description
          "CR5D00TBXF71.";
      }
      enum "CR5D00TFXF71" {
        value 1077;
        description
          "CR5D00TFXF71.";
      }
      enum "CR5D0MPUD170" {
        value 1078;
        description
          "CR5D0MPUD170.";
      }
      enum "CR5D0MPUD270" {
        value 1079;
        description
          "CR5D0MPUD270.";
      }
      enum "CX6D0MPUD170" {
        value 1080;
        description
          "CX6D0MPUD170.";
      }
      enum "CX6D0MPUD270" {
        value 1081;
        description
          "CX6D0MPUD270.";
      }
      enum "TNRD0MPUD270" {
        value 1082;
        description
          "TNRD0MPUD270.";
      }
      enum "TNRD0MPUD370" {
        value 1083;
        description
          "TNRD0MPUD370.";
      }
      enum "ME0D00MPUD71" {
        value 1084;
        description
          "ME0D00MPUD71.";
      }
      enum "ME0D00MPUD72" {
        value 1085;
        description
          "ME0D00MPUD72.";
      }
      enum "CR5D0MPUD470" {
        value 1086;
        description
          "CR5D0MPUD470.";
      }
      enum "CX6D0MPUD470" {
        value 1087;
        description
          "CX6D0MPUD470.";
      }
      enum "TNRD0MPUD470" {
        value 1088;
        description
          "TNRD0MPUD470.";
      }
      enum "ME0P0MPUD470" {
        value 1089;
        description
          "ME0P0MPUD470.";
      }
      enum "CR5D00D2NT70" {
        value 1090;
        description
          "CR5D00D2NT70.";
      }
      enum "CR5DLPUFE070" {
        value 1091;
        description
          "CR5DLPUFE070.";
      }
      enum "TNRD0SRUA870" {
        value 1092;
        description
          "TNRD0SRUA870.";
      }
      enum "TNRDSFUIM07C" {
        value 1093;
        description
          "TNRDSFUIM07C.";
      }
      enum "CR5DSFUIT27B" {
        value 1094;
        description
          "CR5DSFUIT27B.";
      }
      enum "TNRD0SRUA970" {
        value 1095;
        description
          "TNRD0SRUA970.";
      }
      enum "TNRDSFUIU07C" {
        value 1096;
        description
          "TNRDSFUIU07C.";
      }
      enum "ME0D0SRUA870" {
        value 1097;
        description
          "ME0D0SRUA870.";
      }
      enum "ME0D0SRUA970" {
        value 1098;
        description
          "ME0D0SRUA970.";
      }
      enum "ME0DSFUIU07C" {
        value 1099;
        description
          "ME0DSFUIU07C.";
      }
      enum "ME0DSFUIK07B" {
        value 1100;
        description
          "ME0DSFUIK07B.";
      }
      enum "TNRD0MPUB470" {
        value 1101;
        description
          "TNRD0MPUB470.";
      }
      enum "TNRD0MPUB570" {
        value 1102;
        description
          "TNRD0MPUB570.";
      }
      enum "TNRDSFUIE07B" {
        value 1103;
        description
          "TNRDSFUIE07B.";
      }
      enum "ME0D0MPUB570" {
        value 1104;
        description
          "ME0D0MPUB570.";
      }
      enum "ME0DSFUIE07B" {
        value 1105;
        description
          "ME0DSFUIE07B.";
      }
      enum "TNRD0SRUA570" {
        value 1106;
        description
          "TNRD0SRUA570.";
      }
      enum "TNRDSFUIE07C" {
        value 1107;
        description
          "TNRDSFUIE07C.";
      }
      enum "TNRDSFUIM07B" {
        value 1108;
        description
          "TNRDSFUIM07B.";
      }
      enum "TNRDSFUIU07B" {
        value 1109;
        description
          "TNRDSFUIU07B.";
      }
      enum "ME0DSFUIU07B" {
        value 1110;
        description
          "ME0DSFUIU07B.";
      }
      enum "ME0DSFUIK07A" {
        value 1111;
        description
          "ME0DSFUIK07A.";
      }
      enum "ME0D0MPUB470" {
        value 1112;
        description
          "ME0D0MPUB470.";
      }
      enum "ME0DSFUIE07D" {
        value 1113;
        description
          "ME0DSFUIE07D.";
      }
      enum "ME0D0SRUA570" {
        value 1114;
        description
          "ME0D0SRUA570.";
      }
      enum "ME0DSFUIE07C" {
        value 1115;
        description
          "ME0DSFUIE07C.";
      }
      enum "CR5DVSUF8010" {
        value 1116;
        description
          "CR5DVSUF8010.";
      }
      enum "ME0DVSUF8070" {
        value 1117;
        description
          "ME0DVSUF8070.";
      }
      enum "ME0DVSUF8071" {
        value 1118;
        description
          "ME0DVSUF8071.";
      }
      enum "ME0DVSUFD071" {
        value 1119;
        description
          "ME0DVSUFD071.";
      }
      enum "CR5DVSUFD010" {
        value 1120;
        description
          "CR5DVSUFD010.";
      }
      enum "ME0DVSUFD070" {
        value 1121;
        description
          "ME0DVSUFD070.";
      }
      enum "CR5D00SP8010" {
        value 1122;
        description
          "CR5D00SP8010.";
      }
      enum "CR5D00SPD010" {
        value 1123;
        description
          "CR5D00SPD010.";
      }
      enum "ME0D00SP8070" {
        value 1124;
        description
          "ME0D00SP8070.";
      }
      enum "ME0D00SPD070" {
        value 1125;
        description
          "ME0D00SPD070.";
      }
      enum "ME0D00SP8071" {
        value 1126;
        description
          "ME0D00SP8071.";
      }
      enum "ME0D00SPD071" {
        value 1127;
        description
          "ME0D00SPD071.";
      }
      enum "CR5DLPUFK062" {
        value 1128;
        description
          "CR5DLPUFK062.";
      }
      enum "CR5D00N8NC60" {
        value 1129;
        description
          "CR5D00N8NC60.";
      }
      enum "CR5D00N8NC61" {
        value 1130;
        description
          "CR5D00N8NC61.";
      }
      enum "CR5D00L4NC60" {
        value 1131;
        description
          "CR5D00L4NC60.";
      }
      enum "CR5D00LKXF60" {
        value 1132;
        description
          "CR5D00LKXF60.";
      }
      enum "CR5DL2NLEX60" {
        value 1133;
        description
          "CR5DL2NLEX60.";
      }
      enum "CR5DE2NLEX80" {
        value 1134;
        description
          "CR5DE2NLEX80.";
      }
      enum "CX6B0BKP0371" {
        value 1135;
        description
          "CX6B0BKP0371.";
      }
      enum "CX6B0BKP0372" {
        value 1136;
        description
          "CX6B0BKP0372.";
      }
      enum "CR5B0BKP0371" {
        value 1137;
        description
          "CR5B0BKP0371.";
      }
      enum "CR5D00L2NC63" {
        value 1138;
        description
          "CR5D00L2NC63.";
      }
      enum "CR5D00LEXF63" {
        value 1139;
        description
          "CR5D00LEXF63.";
      }
      enum "CR5B0BKP0372" {
        value 1140;
        description
          "CR5B0BKP0372.";
      }
      enum "CR2B0BKP0210" {
        value 1141;
        description
          "CR2B0BKP0210.";
      }
      enum "CR2B0BKP0211" {
        value 1142;
        description
          "CR2B0BKP0211.";
      }
      enum "TNRB0BKP0371" {
        value 1143;
        description
          "TNRB0BKP0371.";
      }
      enum "TNRB0BKP0372" {
        value 1144;
        description
          "TNRB0BKP0372.";
      }
      enum "CX6D0E8GFA10" {
        value 1145;
        description
          "CX6D0E8GFA10.";
      }
      enum "CX6D00CFE110" {
        value 1146;
        description
          "CX6D00CFE110.";
      }
      enum "CX6D00C2CF10" {
        value 1147;
        description
          "CX6D00C2CF10.";
      }
      enum "CR53C2CF0" {
        value 1148;
        description
          "CR53C2CF0.";
      }
      enum "CX6D0L5XFA10" {
        value 1149;
        description
          "CX6D0L5XFA10.";
      }
      enum "CX6D0L2XFA11" {
        value 1150;
        description
          "CX6D0L2XFA11.";
      }
      enum "CX6D0EFGFA10" {
        value 1151;
        description
          "CX6D0EFGFA10.";
      }
      enum "CX6D0EEGEA10" {
        value 1152;
        description
          "CX6D0EEGEA10.";
      }
      enum "CX6DL1XESG1A" {
        value 1153;
        description
          "CX6DL1XESG1A.";
      }
      enum "CX6DL2XEAG1A" {
        value 1154;
        description
          "CX6DL2XEAG1A.";
      }
      enum "CX6D0L5XFA12" {
        value 1155;
        description
          "CX6D0L5XFA12.";
      }
      enum "CX6D0EFGFA11" {
        value 1156;
        description
          "CX6D0EFGFA11.";
      }
      enum "CX6D0E1NCA10" {
        value 1157;
        description
          "CX6D0E1NCA10.";
      }
      enum "CX6D0E1MCA10" {
        value 1158;
        description
          "CX6D0E1MCA10.";
      }
      enum "CX6D0L5XFH10" {
        value 1159;
        description
          "CX6D0L5XFH10.";
      }
      enum "CX6D0L6XFA10" {
        value 1160;
        description
          "CX6D0L6XFA10.";
      }
      enum "CX6D0LBXFA10" {
        value 1161;
        description
          "CX6D0LBXFA10.";
      }
      enum "CX6D0LAXFA12" {
        value 1162;
        description
          "CX6D0LAXFA12.";
      }
      enum "CX6D0E3MFA10" {
        value 1163;
        description
          "CX6D0E3MFA10.";
      }
      enum "CX6D0LAXFH10" {
        value 1164;
        description
          "CX6D0LAXFH10.";
      }
      enum "CX6D0LBXFA12" {
        value 1165;
        description
          "CX6D0LBXFA12.";
      }
      enum "CR5D0EFGFE70" {
        value 1166;
        description
          "CR5D0EFGFE70.";
      }
      enum "CR56LEXF3" {
        value 1167;
        description
          "CR56LEXF3.";
      }
      enum "CR5D00E1NC7D" {
        value 1168;
        description
          "CR5D00E1NC7D.";
      }
      enum "CR5D0L5XFE70" {
        value 1169;
        description
          "CR5D0L5XFE70.";
      }
      enum "CR5D0L2XFE70" {
        value 1170;
        description
          "CR5D0L2XFE70.";
      }
      enum "CR5D0L2XFH70" {
        value 1171;
        description
          "CR5D0L2XFH70.";
      }
      enum "CR5D0L5XFE71" {
        value 1172;
        description
          "CR5D0L5XFE71.";
      }
      enum "CR5D0L5XFH70" {
        value 1173;
        description
          "CR5D0L5XFH70.";
      }
      enum "CR5D0E3MFA70" {
        value 1174;
        description
          "CR5D0E3MFA70.";
      }
      enum "CR5D0LAXFH70" {
        value 1175;
        description
          "CR5D0LAXFH70.";
      }
      enum "CR57EFGFE2" {
        value 1176;
        description
          "CR57EFGFE2.";
      }
      enum "CR57L2XFE2" {
        value 1177;
        description
          "CR57L2XFE2.";
      }
      enum "CR57LEXFE01" {
        value 1178;
        description
          "CR57LEXFE01.";
      }
      enum "CR57L3XFA2" {
        value 1179;
        description
          "CR57L3XFA2.";
      }
      enum "CR57L5XFE2" {
        value 1180;
        description
          "CR57L5XFE2.";
      }
      enum "CR57E3MB2" {
        value 1181;
        description
          "CR57E3MB2.";
      }
      enum "CR53P1XX0" {
        value 1182;
        description
          "CR53P1XX0.";
      }
      enum "CR53P2UF0" {
        value 1183;
        description
          "CR53P2UF0.";
      }
      enum "CR53P4UF0" {
        value 1184;
        description
          "CR53P4UF0.";
      }
      enum "CR53P4HF0" {
        value 1185;
        description
          "CR53P4HF0.";
      }
      enum "CR53P8HF0" {
        value 1186;
        description
          "CR53P8HF0.";
      }
      enum "CR5DVSUID010" {
        value 1187;
        description
          "CR5DVSUID010.";
      }
      enum "ME0DVSUID070" {
        value 1188;
        description
          "ME0DVSUID070.";
      }
      enum "ME0D0VSE0070" {
        value 1189;
        description
          "ME0D0VSE0070.";
      }
      enum "CR58E8NCD" {
        value 1190;
        description
          "CR58E8NCD.";
      }
      enum "CR58EFMBD" {
        value 1191;
        description
          "CR58EFMBD.";
      }
      enum "CR58EPXFB" {
        value 1192;
        description
          "CR58EPXFB.";
      }
      enum "CR56E8NCB" {
        value 1193;
        description
          "CR56E8NCB.";
      }
      enum "CR56EFMBB" {
        value 1194;
        description
          "CR56EFMBB.";
      }
      enum "ME0DVSUF8072" {
        value 1195;
        description
          "ME0DVSUF8072.";
      }
      enum "ME0DVSUF8073" {
        value 1196;
        description
          "ME0DVSUF8073.";
      }
      enum "CR5DVSUF8011" {
        value 1197;
        description
          "CR5DVSUF8011.";
      }
      enum "CR5D0EMGFA7P" {
        value 1198;
        description
          "CR5D0EMGFA7P.";
      }
      enum "CR5D00LBXF7P" {
        value 1199;
        description
          "CR5D00LBXF7P.";
      }
      enum "CR5DL6XEFG7P" {
        value 1200;
        description
          "CR5DL6XEFG7P.";
      }
      enum "CR5D00LFXF7P" {
        value 1201;
        description
          "CR5D00LFXF7P.";
      }
      enum "CR5D00E8NC7P" {
        value 1202;
        description
          "CR5D00E8NC7P.";
      }
      enum "CX6D0L5XFA1B" {
        value 1203;
        description
          "CX6D0L5XFA1B.";
      }
      enum "CX6D0EMGFA1B" {
        value 1204;
        description
          "CX6D0EMGFA1B.";
      }
      enum "CX6DISUFA110" {
        value 1205;
        description
          "CX6DISUFA110.";
      }
      enum "CX6DISUFA210" {
        value 1206;
        description
          "CX6DISUFA210.";
      }
      enum "CX6DISUFB010" {
        value 1207;
        description
          "CX6DISUFB010.";
      }
      enum "CX6D0LAXFA10" {
        value 1208;
        description
          "CX6D0LAXFA10.";
      }
      enum "CX6D0LBXFA11" {
        value 1209;
        description
          "CX6D0LBXFA11.";
      }
      enum "CR5DLAXFAJ7E" {
        value 1210;
        description
          "CR5DLAXFAJ7E.";
      }
      enum "CR5DL2XEFG7E" {
        value 1211;
        description
          "CR5DL2XEFG7E.";
      }
      enum "CX6DISUFE012" {
        value 1212;
        description
          "CX6DISUFE012.";
      }
      enum "CX6DISUFE013" {
        value 1213;
        description
          "CX6DISUFE013.";
      }
      enum "CX6DISUFE011" {
        value 1214;
        description
          "CX6DISUFE011.";
      }
      enum "CX6DISUFF010" {
        value 1215;
        description
          "CX6DISUFF010.";
      }
      enum "CX6D0LFXFA10" {
        value 1216;
        description
          "CX6D0LFXFA10.";
      }
      enum "CX6DISUF5110" {
        value 1217;
        description
          "CX6DISUF5110.";
      }
      enum "CX6DISUF511B" {
        value 1218;
        description
          "CX6DISUF511B.";
      }
      enum "CX6DSFUIE07C" {
        value 1219;
        description
          "CX6DSFUIE07C.";
      }
      enum "CX6DSFUIA07D" {
        value 1220;
        description
          "CX6DSFUIA07D.";
      }
      enum "CX6D0SRUA511" {
        value 1221;
        description
          "CX6D0SRUA511.";
      }
      enum "CX6D0SRUA770" {
        value 1222;
        description
          "CX6D0SRUA770.";
      }
      enum "CX6D0LEXFA10" {
        value 1223;
        description
          "CX6D0LEXFA10.";
      }
      enum "CX6DSFUIE07B" {
        value 1224;
        description
          "CX6DSFUIE07B.";
      }
      enum "CR5D0SRUA770" {
        value 1225;
        description
          "CR5D0SRUA770.";
      }
      enum "CX6D0MPUB411" {
        value 1226;
        description
          "CX6D0MPUB411.";
      }
      enum "CR5D0SRUB570" {
        value 1227;
        description
          "CR5D0SRUB570.";
      }
      enum "CR5D0SRUB571" {
        value 1228;
        description
          "CR5D0SRUB571.";
      }
      enum "CX6D0SRUB510" {
        value 1229;
        description
          "CX6D0SRUB510.";
      }
      enum "ME0D0SRUB570" {
        value 1230;
        description
          "ME0D0SRUB570.";
      }
      enum "TNRD0SRUB570" {
        value 1231;
        description
          "TNRD0SRUB570.";
      }
      enum "CX6DISUFM010" {
        value 1232;
        description
          "CX6DISUFM010.";
      }
      enum "CR5DSFUIA07D" {
        value 1233;
        description
          "CR5DSFUIA07D.";
      }
      enum "CR5DLPUFM07B" {
        value 1234;
        description
          "CR5DLPUFM07B.";
      }
      enum "CR5DLPUFME71" {
        value 1235;
        description
          "CR5DLPUFME71.";
      }
      enum "CR5DLPUFK071" {
        value 1236;
        description
          "CR5DLPUFK071.";
      }
      enum "CR5DLPUFM071" {
        value 1237;
        description
          "CR5DLPUFM071.";
      }
      enum "CR5DLPUFM17B" {
        value 1238;
        description
          "CR5DLPUFM17B.";
      }
      enum "CR5D00LMXF71" {
        value 1239;
        description
          "CR5D00LMXF71.";
      }
      enum "CR5DE2NLFX74" {
        value 1240;
        description
          "CR5DE2NLFX74.";
      }
      enum "CR5D00E4NC71" {
        value 1241;
        description
          "CR5D00E4NC71.";
      }
      enum "CR5D01LMXF7B" {
        value 1242;
        description
          "CR5D01LMXF7B.";
      }
      enum "CR5DE2NLFX75" {
        value 1243;
        description
          "CR5DE2NLFX75.";
      }
      enum "CR5D01E4NC7B" {
        value 1244;
        description
          "CR5D01E4NC7B.";
      }
      enum "CR5D01LMXF7C" {
        value 1245;
        description
          "CR5D01LMXF7C.";
      }
      enum "CR5DE2NLFX76" {
        value 1246;
        description
          "CR5DE2NLFX76.";
      }
      enum "CR5D01E4NC7C" {
        value 1247;
        description
          "CR5D01E4NC7C.";
      }
      enum "CR5D00D4NC71" {
        value 1248;
        description
          "CR5D00D4NC71.";
      }
      enum "CR5D00E4NC7Q" {
        value 1249;
        description
          "CR5D00E4NC7Q.";
      }
      enum "CX6DISUFM011" {
        value 1250;
        description
          "CX6DISUFM011.";
      }
      enum "ME0DBSUFM071" {
        value 1251;
        description
          "ME0DBSUFM071.";
      }
      enum "ME0DBSUFK071" {
        value 1252;
        description
          "ME0DBSUFK071.";
      }
      enum "ME0DMSUFM071" {
        value 1253;
        description
          "ME0DMSUFM071.";
      }
      enum "ME0D0L4NCB71" {
        value 1254;
        description
          "ME0D0L4NCB71.";
      }
      enum "ME0D0LKXFB71" {
        value 1255;
        description
          "ME0D0LKXFB71.";
      }
      enum "ME0D0E4NCM71" {
        value 1256;
        description
          "ME0D0E4NCM71.";
      }
      enum "ME0D0LMXFA71" {
        value 1257;
        description
          "ME0D0LMXFA71.";
      }
      enum "CR5D00LMXF7B" {
        value 1258;
        description
          "CR5D00LMXF7B.";
      }
      enum "CR5DE2NLFX7B" {
        value 1259;
        description
          "CR5DE2NLFX7B.";
      }
      enum "CR5D00E4NC7B" {
        value 1260;
        description
          "CR5D00E4NC7B.";
      }
      enum "CX6D0LEXFA11" {
        value 1261;
        description
          "CX6D0LEXFA11.";
      }
      enum "CR5D00E8NC7C" {
        value 1262;
        description
          "CR5D00E8NC7C.";
      }
      enum "CR5D00LMXF7C" {
        value 1263;
        description
          "CR5D00LMXF7C.";
      }
      enum "CR5DE2NLFX7C" {
        value 1264;
        description
          "CR5DE2NLFX7C.";
      }
      enum "CR5D00E4NC7C" {
        value 1265;
        description
          "CR5D00E4NC7C.";
      }
      enum "ME0DL2XEFG7E" {
        value 1266;
        description
          "ME0DL2XEFG7E.";
      }
      enum "CR5D0L5XFA7E" {
        value 1267;
        description
          "CR5D0L5XFA7E.";
      }
      enum "CR5D0L5XFA7F" {
        value 1268;
        description
          "CR5D0L5XFA7F.";
      }
      enum "CR5DLAXFAJ7F" {
        value 1269;
        description
          "CR5DLAXFAJ7F.";
      }
      enum "ME0D0L5XXE71" {
        value 1270;
        description
          "ME0D0L5XXE71.";
      }
      enum "ME0D0LAXXH71" {
        value 1271;
        description
          "ME0D0LAXXH71.";
      }
      enum "CR5DL2XFFG7E" {
        value 1272;
        description
          "CR5DL2XFFG7E.";
      }
      enum "CR5D0EFGFL70" {
        value 1273;
        description
          "CR5D0EFGFL70.";
      }
      enum "CR5DL5XEFG7L" {
        value 1274;
        description
          "CR5DL5XEFG7L.";
      }
      enum "CR5DL2XEFG71" {
        value 1275;
        description
          "CR5DL2XEFG71.";
      }
      enum "CR5D0EMGFL70" {
        value 1276;
        description
          "CR5D0EMGFL70.";
      }
      enum "CR5DL4XEFG70" {
        value 1277;
        description
          "CR5DL4XEFG70.";
      }
      enum "CR5D0L5XFL70" {
        value 1278;
        description
          "CR5D0L5XFL70.";
      }
      enum "ME0DL2XEFG8E" {
        value 1279;
        description
          "ME0DL2XEFG8E.";
      }
      enum "CX6DSFUIM01B" {
        value 1280;
        description
          "CX6DSFUIM01B.";
      }
      enum "CX6DSFUIM01C" {
        value 1281;
        description
          "CX6DSFUIM01C.";
      }
      enum "CX6D0MPUB510" {
        value 1282;
        description
          "CX6D0MPUB510.";
      }
      enum "CX6D0SRUA810" {
        value 1283;
        description
          "CX6D0SRUA810.";
      }
      enum "CX6D0MPUD410" {
        value 1284;
        description
          "CX6D0MPUD410.";
      }
      enum "ME0DSFUIM07B" {
        value 1285;
        description
          "ME0DSFUIM07B.";
      }
      enum "ME0DSFUIM07C" {
        value 1286;
        description
          "ME0DSFUIM07C.";
      }
      enum "ME0D0SRUA770" {
        value 1287;
        description
          "ME0D0SRUA770.";
      }
      enum "ME0DSFUIA07D" {
        value 1288;
        description
          "ME0DSFUIA07D.";
      }
      enum "ME0D00MPUK70" {
        value 1289;
        description
          "ME0D00MPUK70.";
      }
      enum "ME0DBSU24071" {
        value 1290;
        description
          "ME0DBSU24071.";
      }
      enum "CR5D00A2CF70" {
        value 1291;
        description
          "CR5D00A2CF70.";
      }
      enum "CR2D00A2CF10" {
        value 1292;
        description
          "CR2D00A2CF10.";
      }
      enum "CR57SRU200B" {
        value 1293;
        description
          "CR57SRU200B.";
      }
      enum "CR56E8NCE" {
        value 1294;
        description
          "CR56E8NCE.";
      }
      enum "CR56E2NCC3" {
        value 1295;
        description
          "CR56E2NCC3.";
      }
      enum "CR56E8NLDXA" {
        value 1296;
        description
          "CR56E8NLDXA.";
      }
      enum "CR56EDNBV" {
        value 1297;
        description
          "CR56EDNBV.";
      }
      enum "CR56EDNLIXV" {
        value 1298;
        description
          "CR56EDNLIXV.";
      }
      enum "CR5D0MPUB571" {
        value 1299;
        description
          "CR5D0MPUB571.";
      }
      enum "CX6D0MPUB571" {
        value 1300;
        description
          "CX6D0MPUB571.";
      }
      enum "TNRD0MPUB571" {
        value 1301;
        description
          "TNRD0MPUB571.";
      }
      enum "ME0D0MPUB571" {
        value 1302;
        description
          "ME0D0MPUB571.";
      }
      enum "CR5DMPUX8670" {
        value 1303;
        description
          "CR5DMPUX8670.";
      }
      enum "CX6DMPUX8670" {
        value 1304;
        description
          "CX6DMPUX8670.";
      }
      enum "ME0DMPUX8670" {
        value 1305;
        description
          "ME0DMPUX8670.";
      }
      enum "TNRDMPUX8670" {
        value 1306;
        description
          "TNRDMPUX8670.";
      }
      enum "CR5D0MPUD471" {
        value 1307;
        description
          "CR5D0MPUD471.";
      }
      enum "CX6D0MPUD471" {
        value 1308;
        description
          "CX6D0MPUD471.";
      }
      enum "TNRD0MPUD471" {
        value 1309;
        description
          "TNRD0MPUD471.";
      }
      enum "CR5D0SRUA871" {
        value 1310;
        description
          "CR5D0SRUA871.";
      }
      enum "CX6D0SRUA871" {
        value 1311;
        description
          "CX6D0SRUA871.";
      }
      enum "TNRD0SRUA871" {
        value 1312;
        description
          "TNRD0SRUA871.";
      }
      enum "ME0D0SRUA871" {
        value 1313;
        description
          "ME0D0SRUA871.";
      }
      enum "CR5D0SRUA971" {
        value 1314;
        description
          "CR5D0SRUA971.";
      }
      enum "CX6D0SRUA971" {
        value 1315;
        description
          "CX6D0SRUA971.";
      }
      enum "TNRD0SRUA971" {
        value 1316;
        description
          "TNRD0SRUA971.";
      }
      enum "ME0D0SRUA971" {
        value 1317;
        description
          "ME0D0SRUA971.";
      }
      enum "CR2D0E8GFH10" {
        value 1318;
        description
          "CR2D0E8GFH10.";
      }
      enum "CR2D0L2XFH11" {
        value 1319;
        description
          "CR2D0L2XFH11.";
      }
      enum "CR5D0L2XFH72" {
        value 1320;
        description
          "CR5D0L2XFH72.";
      }
      enum "CR5D0E8GFH70" {
        value 1321;
        description
          "CR5D0E8GFH70.";
      }
      enum "ME0D0EAGFE70" {
        value 1322;
        description
          "ME0D0EAGFE70.";
      }
      enum "ME0D0L2XFE71" {
        value 1323;
        description
          "ME0D0L2XFE71.";
      }
      enum "CR5D0L5XFE74" {
        value 1324;
        description
          "CR5D0L5XFE74.";
      }
      enum "CR5D0L2XFE75" {
        value 1325;
        description
          "CR5D0L2XFE75.";
      }
      enum "CR5D0L5XFE76" {
        value 1326;
        description
          "CR5D0L5XFE76.";
      }
      enum "ME0D0EFGFE7E" {
        value 1327;
        description
          "ME0D0EFGFE7E.";
      }
      enum "ME0D0L5XXE7E" {
        value 1328;
        description
          "ME0D0L5XXE7E.";
      }
      enum "ME0D0L5XXE8E" {
        value 1329;
        description
          "ME0D0L5XXE8E.";
      }
      enum "ME0D0L2XXE7E" {
        value 1330;
        description
          "ME0D0L2XXE7E.";
      }
      enum "ME0D0L2XFH7H" {
        value 1331;
        description
          "ME0D0L2XFH7H.";
      }
      enum "ME0D0L5XFH7H" {
        value 1332;
        description
          "ME0D0L5XFH7H.";
      }
      enum "CR57L5XFI3" {
        value 1333;
        description
          "CR57L5XFI3.";
      }
      enum "CR57L2XFI2" {
        value 1334;
        description
          "CR57L2XFI2.";
      }
      enum "CR5D00E1NC79" {
        value 1335;
        description
          "CR5D00E1NC79.";
      }
      enum "CR5D00LAXF71" {
        value 1336;
        description
          "CR5D00LAXF71.";
      }
      enum "CR2D00LAXF10" {
        value 1337;
        description
          "CR2D00LAXF10.";
      }
      enum "CR2D00E1NC10" {
        value 1338;
        description
          "CR2D00E1NC10.";
      }
      enum "CR5D1DMD1M01" {
        value 1339;
        description
          "CR5D1DMD1M01.";
      }
      enum "CR5D1DMD1M02" {
        value 1340;
        description
          "CR5D1DMD1M02.";
      }
      enum "CR5D1DMD1M03" {
        value 1341;
        description
          "CR5D1DMD1M03.";
      }
      enum "CR5D1DMD1M04" {
        value 1342;
        description
          "CR5D1DMD1M04.";
      }
      enum "CR5D1DMD1M05" {
        value 1343;
        description
          "CR5D1DMD1M05.";
      }
      enum "CR5D1DMD1M06" {
        value 1344;
        description
          "CR5D1DMD1M06.";
      }
      enum "CR5D1DMD1M07" {
        value 1345;
        description
          "CR5D1DMD1M07.";
      }
      enum "CR5D1DMD1M08" {
        value 1346;
        description
          "CR5D1DMD1M08.";
      }
      enum "CR5D2DMD2M01" {
        value 1347;
        description
          "CR5D2DMD2M01.";
      }
      enum "CR5D2DMD2M02" {
        value 1348;
        description
          "CR5D2DMD2M02.";
      }
      enum "CR5D2DMD2M03" {
        value 1349;
        description
          "CR5D2DMD2M03.";
      }
      enum "CR5D2DMD2M04" {
        value 1350;
        description
          "CR5D2DMD2M04.";
      }
      enum "CR5D0E2NCE70" {
        value 1351;
        description
          "CR5D0E2NCE70.";
      }
      enum "CR5D0LEXFE70" {
        value 1352;
        description
          "CR5D0LEXFE70.";
      }
      enum "ME0M0LEXFB70" {
        value 1353;
        description
          "ME0M0LEXFB70.";
      }
      enum "ME0M0E2NCB70" {
        value 1354;
        description
          "ME0M0E2NCB70.";
      }
      enum "CR57EFGFH2" {
        value 1355;
        description
          "CR57EFGFH2.";
      }
      enum "CR5D0EFGFE71" {
        value 1356;
        description
          "CR5D0EFGFE71.";
      }
      enum "CR58E8NBA" {
        value 1357;
        description
          "CR58E8NBA.";
      }
      enum "CR58D8NCA" {
        value 1358;
        description
          "CR58D8NCA.";
      }
      enum "CX68LGXF0" {
        value 1359;
        description
          "CX68LGXF0.";
      }
      enum "CR5D00E8NB60" {
        value 1360;
        description
          "CR5D00E8NB60.";
      }
      enum "CR5DE2NLEX60" {
        value 1361;
        description
          "CR5DE2NLEX60.";
      }
      enum "CR5D00LFXF60" {
        value 1362;
        description
          "CR5D00LFXF60.";
      }
      enum "CR5D00E4NB60" {
        value 1363;
        description
          "CR5D00E4NB60.";
      }
      enum "CR56E4NBA1" {
        value 1364;
        description
          "CR56E4NBA1.";
      }
      enum "CR5D00N4NC60" {
        value 1365;
        description
          "CR5D00N4NC60.";
      }
      enum "CR5D00LMXB60" {
        value 1366;
        description
          "CR5D00LMXB60.";
      }
      enum "ME0D0L8NCA70" {
        value 1367;
        description
          "ME0D0L8NCA70.";
      }
      enum "ME0D0L4NCB70" {
        value 1368;
        description
          "ME0D0L4NCB70.";
      }
      enum "ME0D0L2NCB70" {
        value 1369;
        description
          "ME0D0L2NCB70.";
      }
      enum "ME0D0LFXFA70" {
        value 1370;
        description
          "ME0D0LFXFA70.";
      }
      enum "ME0D0LMXFA70" {
        value 1371;
        description
          "ME0D0LMXFA70.";
      }
      enum "ME0D0E4NCM70" {
        value 1372;
        description
          "ME0D0E4NCM70.";
      }
      enum "ME0D0LKXFB70" {
        value 1373;
        description
          "ME0D0LKXFB70.";
      }
      enum "ME0DE2NLEX7B" {
        value 1374;
        description
          "ME0DE2NLEX7B.";
      }
      enum "ME0DL3XEFG7B" {
        value 1375;
        description
          "ME0DL3XEFG7B.";
      }
      enum "ME0D0LEXFB71" {
        value 1376;
        description
          "ME0D0LEXFB71.";
      }
      enum "ME0D0LAXFA70" {
        value 1377;
        description
          "ME0D0LAXFA70.";
      }
      enum "ME0D0LEXFB70" {
        value 1378;
        description
          "ME0D0LEXFB70.";
      }
      enum "ME0D0E2NCB70" {
        value 1379;
        description
          "ME0D0E2NCB70.";
      }
      enum "ME0D0EMGFB70" {
        value 1380;
        description
          "ME0D0EMGFB70.";
      }
      enum "ME0D0LAXXB70" {
        value 1381;
        description
          "ME0D0LAXXB70.";
      }
      enum "ME0D0L5XXB70" {
        value 1382;
        description
          "ME0D0L5XXB70.";
      }
      enum "CR5DLPUFE07E" {
        value 1383;
        description
          "CR5DLPUFE07E.";
      }
      enum "ME0DBSUFB070" {
        value 1384;
        description
          "ME0DBSUFB070.";
      }
      enum "ME0DBSUFC870" {
        value 1385;
        description
          "ME0DBSUFC870.";
      }
      enum "ME0DBSUFK070" {
        value 1386;
        description
          "ME0DBSUFK070.";
      }
      enum "CR5DLPUFK070" {
        value 1387;
        description
          "CR5DLPUFK070.";
      }
      enum "CR9DLPUFK080" {
        value 1388;
        description
          "CR9DLPUFK080.";
      }
      enum "CR9D00EDNB8L" {
        value 1389;
        description
          "CR9D00EDNB8L.";
      }
      enum "CR9D00EDNB8P" {
        value 1390;
        description
          "CR9D00EDNB8P.";
      }
      enum "CX6D00EPXFA0" {
        value 1391;
        description
          "CX6D00EPXFA0.";
      }
      enum "CR9D00EKNB80" {
        value 1392;
        description
          "CR9D00EKNB80.";
      }
      enum "CR9DLPUFT280" {
        value 1393;
        description
          "CR9DLPUFT280.";
      }
      enum "CR9D00DDNC80" {
        value 1394;
        description
          "CR9D00DDNC80.";
      }
      enum "CR9D00DDNC8P" {
        value 1395;
        description
          "CR9D00DDNC8P.";
      }
      enum "CR9D00EENB80" {
        value 1396;
        description
          "CR9D00EENB80.";
      }
      enum "CR9D00EENB8P" {
        value 1397;
        description
          "CR9D00EENB8P.";
      }
      enum "CR9D00DDNC8L" {
        value 1398;
        description
          "CR9D00DDNC8L.";
      }
      enum "CR9D00EENB8L" {
        value 1399;
        description
          "CR9D00EENB8L.";
      }
      enum "CR9D00EKNB8P" {
        value 1400;
        description
          "CR9D00EKNB8P.";
      }
      enum "CR9D00EKNB8L" {
        value 1401;
        description
          "CR9D00EKNB8L.";
      }
      enum "CR9D00E8KC80" {
        value 1402;
        description
          "CR9D00E8KC80.";
      }
      enum "CR9D00E8KC8P" {
        value 1403;
        description
          "CR9D00E8KC8P.";
      }
      enum "CR9DE8KE8N8R" {
        value 1404;
        description
          "CR9DE8KE8N8R.";
      }
      enum "CR9D00EKNB8M" {
        value 1405;
        description
          "CR9D00EKNB8M.";
      }
      enum "CX6D00EKNBA1" {
        value 1406;
        description
          "CX6D00EKNBA1.";
      }
      enum "CX6D00EKNBA0" {
        value 1407;
        description
          "CX6D00EKNBA0.";
      }
      enum "CX6D00DDNCA0" {
        value 1408;
        description
          "CX6D00DDNCA0.";
      }
      enum "CX6D00EENBA0" {
        value 1409;
        description
          "CX6D00EENBA0.";
      }
      enum "CR9D00EENB83" {
        value 1410;
        description
          "CR9D00EENB83.";
      }
      enum "CX6D60T220A0" {
        value 1411;
        description
          "CX6D60T220A0.";
      }
      enum "CR9D00E8NC8P" {
        value 1412;
        description
          "CR9D00E8NC8P.";
      }
      enum "CR9D00D8NC8P" {
        value 1413;
        description
          "CR9D00D8NC8P.";
      }
      enum "CR9D00EPXF8P" {
        value 1414;
        description
          "CR9D00EPXF8P.";
      }
      enum "CR5D00LKXF6P" {
        value 1415;
        description
          "CR5D00LKXF6P.";
      }
      enum "CR5D00EDNB6P" {
        value 1416;
        description
          "CR5D00EDNB6P.";
      }
      enum "CR5D0EFGFH70" {
        value 1417;
        description
          "CR5D0EFGFH70.";
      }
      enum "ME0D0EFGFH7H" {
        value 1418;
        description
          "ME0D0EFGFH7H.";
      }
      enum "CR5D0L2XFH73" {
        value 1419;
        description
          "CR5D0L2XFH73.";
      }
      enum "ME0D0L2XFH8H" {
        value 1420;
        description
          "ME0D0L2XFH8H.";
      }
      enum "CR5D0L5XFH72" {
        value 1421;
        description
          "CR5D0L5XFH72.";
      }
      enum "ME0D0L5XFH8H" {
        value 1422;
        description
          "ME0D0L5XFH8H.";
      }
      enum "CR5D0EAGFE70" {
        value 1423;
        description
          "CR5D0EAGFE70.";
      }
      enum "CR5D0L2XFE71" {
        value 1424;
        description
          "CR5D0L2XFE71.";
      }
      enum "CR5D00LAXF90" {
        value 1425;
        description
          "CR5D00LAXF90.";
      }
      enum "CR5D00LEXF6B" {
        value 1426;
        description
          "CR5D00LEXF6B.";
      }
      enum "CR5D00E5MF6B" {
        value 1427;
        description
          "CR5D00E5MF6B.";
      }
      enum "CR5D00E1NC98" {
        value 1428;
        description
          "CR5D00E1NC98.";
      }
      enum "CR2D04OTU210" {
        value 1429;
        description
          "CR2D04OTU210.";
      }
      enum "CR2D0E5XMF10" {
        value 1430;
        description
          "CR2D0E5XMF10.";
      }
      enum "CR2D00LAXF11" {
        value 1431;
        description
          "CR2D00LAXF11.";
      }
      enum "CR2D00E1NC11" {
        value 1432;
        description
          "CR2D00E1NC11.";
      }
      enum "CR2D00E2NF10" {
        value 1433;
        description
          "CR2D00E2NF10.";
      }
      enum "CR5D00E2NF90" {
        value 1434;
        description
          "CR5D00E2NF90.";
      }
      enum "CX6D0E2NBA10" {
        value 1435;
        description
          "CX6D0E2NBA10.";
      }
      enum "CX6DE2VE1N10" {
        value 1436;
        description
          "CX6DE2VE1N10.";
      }
      enum "ME0M0E2NFB70" {
        value 1437;
        description
          "ME0M0E2NFB70.";
      }
      enum "ME0M0E2NFB71" {
        value 1438;
        description
          "ME0M0E2NFB71.";
      }
      enum "CR57L6XE4GF0" {
        value 1439;
        description
          "CR57L6XE4GF0.";
      }
      enum "CR57E4GFC0" {
        value 1440;
        description
          "CR57E4GFC0.";
      }
      enum "CR5D00E1NC77" {
        value 1441;
        description
          "CR5D00E1NC77.";
      }
      enum "CR5D00E1NC7A" {
        value 1442;
        description
          "CR5D00E1NC7A.";
      }
      enum "ME0D0E1NCB70" {
        value 1443;
        description
          "ME0D0E1NCB70.";
      }
      enum "ME0D0E1NCB71" {
        value 1444;
        description
          "ME0D0E1NCB71.";
      }
      enum "CR57E1NCF2" {
        value 1445;
        description
          "CR57E1NCF2.";
      }
      enum "CX6D0E1NCA11" {
        value 1446;
        description
          "CX6D0E1NCA11.";
      }
      enum "CR5D00E1ND70" {
        value 1447;
        description
          "CR5D00E1ND70.";
      }
      enum "CR5D00E1ND73" {
        value 1448;
        description
          "CR5D00E1ND73.";
      }
      enum "ME0D0E1NDB70" {
        value 1449;
        description
          "ME0D0E1NDB70.";
      }
      enum "ME0D0E1NDB71" {
        value 1450;
        description
          "ME0D0E1NDB71.";
      }
      enum "CX6D0E1NBA10" {
        value 1451;
        description
          "CX6D0E1NBA10.";
      }
      enum "CR5D00E2NB60" {
        value 1452;
        description
          "CR5D00E2NB60.";
      }
      enum "CR5D00E2NF70" {
        value 1453;
        description
          "CR5D00E2NF70.";
      }
      enum "CR5D3DMR4M01" {
        value 1454;
        description
          "CR5D3DMR4M01.";
      }
      enum "CR5D3DMR4M02" {
        value 1455;
        description
          "CR5D3DMR4M02.";
      }
      enum "CR5DBMC4XV91" {
        value 1456;
        description
          "CR5DBMC4XV91.";
      }
      enum "CR5DBMC4XV92" {
        value 1457;
        description
          "CR5DBMC4XV92.";
      }
      enum "CR5D00MD8A70" {
        value 1458;
        description
          "CR5D00MD8A70.";
      }
      enum "CR2D0EAGFE10" {
        value 1459;
        description
          "CR2D0EAGFE10.";
      }
      enum "CR2D0L2XFE10" {
        value 1460;
        description
          "CR2D0L2XFE10.";
      }
      enum "CR5D0E2NCE71" {
        value 1461;
        description
          "CR5D0E2NCE71.";
      }
      enum "ME0M0E2NCB71" {
        value 1462;
        description
          "ME0M0E2NCB71.";
      }
      enum "CR5D0LEXFE71" {
        value 1463;
        description
          "CR5D0LEXFE71.";
      }
      enum "CR5D0LEXFE72" {
        value 1464;
        description
          "CR5D0LEXFE72.";
      }
      enum "CR5D0LAXFE71" {
        value 1465;
        description
          "CR5D0LAXFE71.";
      }
      enum "ME0M0LEXFB71" {
        value 1466;
        description
          "ME0M0LEXFB71.";
      }
      enum "CR5D0L6XFH70" {
        value 1467;
        description
          "CR5D0L6XFH70.";
      }
      enum "CR5D0L5XFH71" {
        value 1468;
        description
          "CR5D0L5XFH71.";
      }
      enum "CX6D0L5XFH11" {
        value 1469;
        description
          "CX6D0L5XFH11.";
      }
      enum "ME0D0L5XFH7F" {
        value 1470;
        description
          "ME0D0L5XFH7F.";
      }
      enum "ME0D0L6XFH7H" {
        value 1471;
        description
          "ME0D0L6XFH7H.";
      }
      enum "ME0D0L6XFE7E" {
        value 1472;
        description
          "ME0D0L6XFE7E.";
      }
      enum "CR5D0LBXFH70" {
        value 1473;
        description
          "CR5D0LBXFH70.";
      }
      enum "ME0D0LBXFH7H" {
        value 1474;
        description
          "ME0D0LBXFH7H.";
      }
      enum "CR5D00N6GF60" {
        value 1475;
        description
          "CR5D00N6GF60.";
      }
      enum "CR5D00NBGF60" {
        value 1476;
        description
          "CR5D00NBGF60.";
      }
      enum "CR9D00LFXF80" {
        value 1477;
        description
          "CR9D00LFXF80.";
      }
      enum "CR9D00NBXF80" {
        value 1478;
        description
          "CR9D00NBXF80.";
      }
      enum "CX6D00NBXFA0" {
        value 1479;
        description
          "CX6D00NBXFA0.";
      }
      enum "CR9D00N6XF80" {
        value 1480;
        description
          "CR9D00N6XF80.";
      }
      enum "CR9D00P8UF80" {
        value 1481;
        description
          "CR9D00P8UF80.";
      }
      enum "CR9D00P4XX80" {
        value 1482;
        description
          "CR9D00P4XX80.";
      }
      enum "CR5D00EEGF71" {
        value 1483;
        description
          "CR5D00EEGF71.";
      }
      enum "CR2D00EEGF11" {
        value 1484;
        description
          "CR2D00EEGF11.";
      }
      enum "CX6D00EEGF10" {
        value 1485;
        description
          "CX6D00EEGF10.";
      }
      enum "CR57EFGFH3" {
        value 1486;
        description
          "CR57EFGFH3.";
      }
      enum "CR57L6XFI02" {
        value 1487;
        description
          "CR57L6XFI02.";
      }
      enum "CR5D0L6XFE70" {
        value 1488;
        description
          "CR5D0L6XFE70.";
      }
      enum "CR58EANBB" {
        value 1489;
        description
          "CR58EANBB.";
      }
      enum "CR57LBXFE2" {
        value 1490;
        description
          "CR57LBXFE2.";
      }
      enum "CR57E8NCB1" {
        value 1491;
        description
          "CR57E8NCB1.";
      }
      enum "CR58EENBA0" {
        value 1492;
        description
          "CR58EENBA0.";
      }
      enum "CR58D8NCB" {
        value 1493;
        description
          "CR58D8NCB.";
      }
      enum "CR58E4KCA0" {
        value 1494;
        description
          "CR58E4KCA0.";
      }
      enum "CR58D8NCB0" {
        value 1495;
        description
          "CR58D8NCB0.";
      }
      enum "CR9D00D8KC80" {
        value 1496;
        description
          "CR9D00D8KC80.";
      }
      enum "CR57EENBE0" {
        value 1497;
        description
          "CR57EENBE0.";
      }
      enum "CR5DE2VE1N70" {
        value 1498;
        description
          "CR5DE2VE1N70.";
      }
      enum "CR5D0E5XMF90" {
        value 1499;
        description
          "CR5D0E5XMF90.";
      }
      enum "CR5D00E8NC64" {
        value 1500;
        description
          "CR5D00E8NC64.";
      }
      enum "CR5D00E8NB61" {
        value 1501;
        description
          "CR5D00E8NB61.";
      }
      enum "CR5D00E8NB63" {
        value 1502;
        description
          "CR5D00E8NB63.";
      }
      enum "CR5D00E2KC61" {
        value 1503;
        description
          "CR5D00E2KC61.";
      }
      enum "CR5D00E8NC65" {
        value 1504;
        description
          "CR5D00E8NC65.";
      }
      enum "CR5D00LJXF61" {
        value 1505;
        description
          "CR5D00LJXF61.";
      }
      enum "CR5D00LJXF60" {
        value 1506;
        description
          "CR5D00LJXF60.";
    }
      enum "CR5D00E4NB63" {
        value 1507;
        description
          "CR5D00E4NB63.";
      }
      enum "CR5D00LFXF63" {
        value 1508;
        description
          "CR5D00LFXF63.";
      }
      enum "CR5D00E2NC63" {
        value 1509;
        description
          "CR5D00E2NC63.";
      }
      enum "CR5D00LEXF65" {
        value 1510;
        description
          "CR5D00LEXF65.";
      }
      enum "CR5D00E2KC60" {
        value 1511;
        description
          "CR5D00E2KC60.";
      }
      enum "fname8090CX6620" {
        value 1512;
        description
          "CX6620 Chassis.";
      }
      enum "fname8090CX6608" {
        value 1513;
        description
          "CX6608 Chassis.";
      }
      enum "CR5D04OTU290" {
        value 1514;
        description
          "CR5D04OTU290.";
      }
      enum "CR5D00P4XX60" {
        value 1515;
        description
          "CR5D00P4XX60.";
      }
      enum "CR5D00LFXF76" {
        value 1516;
        description
          "CR5D00LFXF76.";
      }
      enum "CR5D00LFXF75" {
        value 1517;
        description
          "CR5D00LFXF75.";
      }
      enum "CX6D00LFXF10" {
        value 1518;
        description
          "CX6D00LFXF10.";
      }
      enum "ME0D00LFXF70" {
        value 1519;
        description
          "ME0D00LFXF70.";
      }
      enum "CR5D00E2NC78" {
        value 1520;
        description
          "CR5D00E2NC78.";
      }
      enum "CR5D00E2NC79" {
        value 1521;
        description
          "CR5D00E2NC79.";
      }
      enum "CX6D00E2NC10" {
        value 1522;
        description
          "CX6D00E2NC10.";
      }
      enum "ME0D00E2NC78" {
        value 1523;
        description
          "ME0D00E2NC78.";
      }
      enum "CR5D00E2NF71" {
        value 1524;
        description
          "CR5D00E2NF71.";
      }
      enum "CR5D00E2NF72" {
        value 1525;
        description
          "CR5D00E2NF72.";
      }
      enum "CX6D00E2NF10" {
        value 1526;
        description
          "CX6D00E2NF10.";
      }
      enum "ME0D00E2NF71" {
        value 1527;
        description
          "ME0D00E2NF71.";
      }
      enum "CR9D00N2NC80" {
        value 1528;
        description
          "CR9D00N2NC80.";
      }
      enum "CX6D00N2NCA0" {
        value 1529;
        description
          "CX6D00N2NCA0.";
      }
      enum "CR5D00E2NC77" {
        value 1530;
        description
          "CR5D00E2NC77.";
      }
      enum "UNKNOWN_SUBCARD" {
        value 1531;
        description
          "UNKNOWN_SUBCARD.";
      }
      enum "ANDD16E11202" {
        value 1532;
        description
          "ANDD16E11202.";
      }
      enum "ANDD16E17502" {
        value 1533;
        description
          "ANDD16E17502.";
      }
      enum "ANDD32E11202" {
        value 1534;
        description
          "ANDD32E11202.";
      }
      enum "ANDD32E17502" {
        value 1535;
        description
          "ANDD32E17502.";
      }
      enum "ANDD000EX2S0" {
        value 1536;
        description
          "ANDD000EX2S0.";
      }
      enum "ANDD000EX1S0" {
        value 1537;
        description
          "ANDD000EX1S0.";
      }
      enum "ANJ1EXL1" {
        value 1538;
        description
          "ANJ1EXL1.";
      }
      enum "ANDD00EM4T01" {
        value 1539;
        description
          "ANDD00EM4T01.";
      }
      enum "ANDD00EM8T01" {
        value 1540;
        description
          "ANDD00EM8T01.";
      }
      enum "ANDD00EM4F01" {
        value 1541;
        description
          "ANDD00EM4F01.";
      }
      enum "ANDD00EM8F01" {
        value 1542;
        description
          "ANDD00EM8F01.";
      }
      enum "ANKD00EX2S00" {
        value 1543;
        description
          "ANKD00EX2S00.";
      }
      enum "ANJD01XE8F00" {
        value 1544;
        description
          "ANJD01XE8F00.";
      }
      enum "CARD ATN 910C-A" {
        value 1545;
        description
          "CARD ATN 910C-A.";
      }
      enum "CARD ATN 910C-B" {
        value 1546;
        description
          "CARD ATN 910C-B.";
      }
      enum "CARD NE05E-SQ" {
        value 1547;
        description
          "CARD NE05E-SQ.";
      }
      enum "LNDD01XE8F00" {
        value 1548;
        description
          "LNDD01XE8F00.";
      }
      enum "ANKD00EX4S00" {
        value 1549;
        description
          "ANKD00EX4S00.";
      }
      enum "NEDD00EX4S00" {
        value 1550;
        description
          "NEDD00EX4S00.";
      }
      enum "ANKD00EM20F0" {
        value 1551;
        description
          "ANKD00EM20F0.";
      }
      enum "ANKD0EM20F00" {
        value 1552;
        description
          "ANKD0EM20F00.";
      }
     enum "CR5D08CWDM70" {
        value 1553;
        description
          "CR5D08CWDM70:";
      }
      enum "CARD1 ATN 910C-D" {
        value 1554;
        description
          "CARD1 ATN 910C-D.";
      }
      enum "ANG2MO1" {
        value 1555;
        description
          "ANG2MO1.";
      }
      enum "ANDD00CQ1B00" {
        value 1556;
        description
          "ANDD00CQ1B00.";
      }
    enum "NEDD16E17502" {
        value 1557;
        description
          "NEDD16E17502.";
      }
    enum "NEDD16E11202" {
        value 1558;
        description
          "NEDD16E11202.";
      }
   enum "NEDD16E17501" {
        value 1559;
        description
          "NEDD16E17501.";
      }
   enum "NEDD16E11201" {
        value 1560;
        description
          "NEDD16E11201.";
      }
    enum "NEDD00EF8T00" {
        value 1561;
        description
          "NEDD00EF8T00.";
      }
    enum "NEDD000EG400" {
        value 1562;
        description
          "NEDD000EG400.";
      }
    enum "NEDD00EG4T00" {
        value 1563;
        description
          "NEDD00EG4T00.";
      }
      enum "NEDD00CQ1B00" {
        value 1564;
        description
          "NEDD00CQ1B00.";
      }
      enum "ANKD001EV200" {
        value 1565;
        description
          "ANKD001EV200.";
      }
      enum "ANKD001EV100" {
        value 1566;
        description
          "ANKD001EV100.";
      }
      enum "ANKD01EXAS00" {
        value 1567;
        description
          "ANKD01EXAS00.";
      }
      enum "ANKD001EH100" {
        value 1568;
        description
          "ANKD001EH100.";
      }
      enum "CX6D00E2XF70" {
        value 1569;
        description
          "CX6D00E2XF70.";
      }
      enum "CR57E1NBA2" {
        value 1570;
        description
          "CR57E1NBA2.";
      }
      enum "CR57LAXFE01" {
        value 1571;
        description
          "CR57LAXFE01.";
      }
      enum "CR57E2NCF1" {
        value 1572;
        description
          "CR57E2NCF1.";
      }
      enum "CR9D00LFXF81" {
        value 1573;
        description
          "CR9D00LFXF81.";
      }
      enum "CX6D0LEXFA12" {
        value 1574;
        description
          "CX6D0LEXFA12.";
      }
      enum "CX6D0E2NCA11" {
        value 1575;
        description
          "CX6D0E2NCA11.";
      }
      enum "CX6D0E2NCA12" {
        value 1576;
        description
          "CX6D0E2NCA12.";
      }
      enum "CR5D0E2NBE71" {
        value 1577;
        description
          "CR5D0E2NBE71.";
      }
      enum "ME0M0E2NCB72" {
        value 1578;
        description
          "ME0M0E2NCB72.";
      }
      enum "CR57E2NBB2" {
        value 1579;
        description
          "CR57E2NBB2.";
      }
      enum "CR5D0E2NFE70" {
        value 1580;
        description
          "CR5D0E2NFE70.";
      }
      enum "CARD ATN 910B-A" {
        value 1581;
        description
          "CARD ATN 910B-A.";
      }
      enum "CARD ATN 910B-B" {
        value 1582;
        description
          "CARD ATN 910B-B.";
      }
      enum "CARD ATN 910B-D" {
        value 1583;
        description
          "CARD ATN 910B-D.";
      }
      enum "CARD ATN 910B-E" {
        value 1584;
        description
          "CARD ATN 910B-E.";
      }
      enum "CARD ATN 910B-F" {
        value 1585;
        description
          "CARD ATN 910B-F.";
      }
    enum "CARD NE05E-S2" {
        value 1586;
        description
          "CARD NE05E-S2.";
      }
      enum "ANDD00EM8F00" {
        value 1587;
        description
          "ANDD00EM8F00.";
      }
      enum "ANDD00EM8T00" {
        value 1588;
        description
          "ANDD00EM8T00.";
      }
      enum "ANDD00EM4F00" {
        value 1589;
        description
          "ANDD00EM4F00.";
      }
      enum "ANDD00EM4T00" {
        value 1590;
        description
          "ANDD00EM4T00.";
      }
      enum "ANDD000EX100" {
        value 1591;
        description
          "ANDD000EX100.";
      }
      enum "ANDD00EM8M00" {
        value 1592;
        description
          "ANDD00EM8M00.";
      }
      enum "NEDD00EM4F01" {
        value 1593;
        description
          "NEDD00EM4F01.";
      }
      enum "NEDD00EM4T01" {
        value 1594;
        description
          "NEDD00EM4T01.";
      }
      enum "NEDD00EM8F01" {
        value 1595;
        description
          "NEDD00EM8F01.";
      }
      enum "NEDD00EM8T01" {
        value 1596;
        description
          "NEDD00EM8T01.";
      }
      enum "NEDD000EX1S0" {
        value 1597;
        description
          "NEDD000EX1S0.";
      }
      enum "NEDD00EX2S00" {
        value 1598;
        description
          "NEDD00EX2S00.";
      }
      enum "NEDD32E17501" {
        value 1599;
        description
          "NEDD32E17501.";
      }
      enum "NEDD32E11201" {
        value 1600;
        description
          "NEDD32E11201.";
      }
      enum "NEDD0EM4TP00" {
        value 1601;
        description
          "NEDD0EM4TP00.";
      }
      enum "ANKD001EY200" {
        value 1602;
        description
          "ANKD001EY200.";
      }
      enum "ANKD001EY400" {
        value 1603;
        description
          "ANKD001EY400.";
      }
     enum "ANKD001EY401" {
        value 1604;
        description
          "ANKD001EY401.";
      }
      enum "ANKD001EV102" {
        value 1605;
        description
          "ANKD001EV102.";
      }
      enum "ANKD001EV104" {
        value 1606;
        description
          "ANKD001EV104.";
      }
      enum "ANKD001EV105" {
        value 1607;
        description
          "ANKD001EV105.";
      }
      enum "ANKD001EV103" {
        value 1608;
        description
          "ANKD001EV103.";
      }
      enum "CR2D00E1NB20" {
        value 1609;
        description
          "CR2D00E1NB20.";
      }
      enum "CR2D00E4XF20" {
        value 1610;
        description
          "CR2D00E4XF20.";
      }
      enum "CR2DE2NE4X10" {
        value 1611;
        description
          "CR2DE2NE4X10.";
      }
      enum "CR2D00LAXF91" {
        value 1612;
        description
          "CR2D00LAXF91.";
      }
      enum "CR2D00E8XM25" {
        value 1613;
        description
          "CR2D00E8XM25.";
      }
      enum "CR2D00E4XM25" {
        value 1614;
        description
          "CR2D00E4XM25.";
      }
      enum "CR2D0E5XMF91" {
        value 1615;
        description
          "CR2D0E5XMF91.";
      }
      enum "ANKD001EV201" {
        value 1616;
        description
          "ANKD001EV201.";
      }
      enum "ANKD01EXAS01" {
        value 1617;
        description
          "ANKD01EXAS01.";
      }
      enum "ANKD001EY201" {
        value 1618;
        description
          "ANKD001EY201.";
      }
      enum "ANKD001EY100" {
        value 1619;
        description
          "ANKD001EY100.";
      }
      enum "CR5D0E5XMF91" {
        value 1620;
        description
          "CR5D0E5XMF91.";
      }
     enum "CR5D0E5XMF93" {
        value 1621;
        description
          "CR5D0E5XMF93.";
      }
     enum "CR5DE2NE4X13" {
        value 1622;
        description
          "CR5DE2NE4X13.";
      }
     enum "ANKD001EV202" {
        value 1623;
        description
          "ANKD001EV202.";
      }
      enum "CR5D00E4XM25" {
        value 1624;
        description
          "CR5D00E4XM25.";
      }
      enum "CR5D00E8XM25" {
        value 1625;
        description
          "CR5D00E8XM25.";
      }
      enum "CR5D00LAXF91" {
        value 1626;
        description
          "CR5D00LAXF91.";
      }
      enum "CX6D0E5XMF91" {
        value 1627;
        description
          "CX6D0E5XMF91.";
      }
      enum "CX6D00E4XF91" {
        value 1628;
        description
          "CX6D00E4XF91.";
      }
      enum "CX6D00E8XF91" {
        value 1629;
        description
          "CX6D00E8XF91.";
      }
      enum "CX6D00LAXF91" {
        value 1630;
        description
          "CX6D00LAXF91.";
      }
      enum "CR5DE4VE2N70" {
        value 1631;
        description
          "CR5DE4VE2N70.";
      }
      enum "CR57E4VBE1" {
        value 1632;
        description
          "CR57E4VBE1.";
      }
      enum "CR57E8VBA1" {
        value 1633;
        description
          "CR57E8VBA1.";
      }
      enum "CR57EDYFA1" {
        value 1634;
        description
          "CR57EDYFA1.";
      }
      enum "CR57EENBC0" {
        value 1635;
        description
          "CR57EENBC0.";
      }
      enum "CR57EENBC1" {
        value 1636;
        description
          "CR57EENBC1.";
      }
      enum "CR58EENBD0" {
        value 1637;
        description
          "CR58EENBD0.";
      }
      enum "CX6DE4VE2N10" {
        value 1638;
        description
          "CX6DE4VE2N10.";
      }
      enum "CR9D00LJXF80" {
        value 1639;
        description
          "CR9D00LJXF80.";
      }
      enum "CR9D00EANB82" {
        value 1640;
        description
          "CR9D00EANB82.";
      }
      enum "CR9D00E5NB80" {
        value 1641;
        description
          "CR9D00E5NB80.";
      }
      enum "CR9D00EDYF80" {
        value 1642;
        description
          "CR9D00EDYF80.";
      }
      enum "ME0D0L5XXE70" {
        value 1643;
        description
          "ME0D0L5XXE70.";
      }
      enum "CR5D0MPUB760" {
        value 1644;
        description
          "CR5D0MPUB760.";
      }
     enum "CR9D00MPUS80" {
        value 1645;
        description
          "CR9D00MPUS80.";
      }
      enum "CR9D00EPXF81" {
        value 1646;
        description
          "CR9D00EPXF81.";
      }
      enum "CR9D000CMU61" {
        value 1647;
        description
          "CR9D000CMU61.";
      }
      enum "CR9D000CMU62" {
        value 1648;
        description
          "CR9D000CMU62.";
      }
      enum "CR5D0MPUN160" {
        value 1649;
        description
          "CR5D0MPUN160.";
      }
      enum "CR5DSFUIT260" {
        value 1650;
        description
          "CR5DSFUIT260.";
      }
      enum "CR9DLPUFK081" {
        value 1651;
        description
          "CR9DLPUFK081.";
      }
      enum "CR9D00EPXF8L" {
        value 1652;
        description
          "CR9D00EPXF8L.";
      }
     enum "ME0D0L5XXM70" {
        value 1653;
        description
          "ME0D0L5XXM70.";
      }
       enum "CR5D00LMXF7P" {
        value 1654;
        description
          "CR5D00LMXF7P.";
      }
     enum "CR5DE2NLFX7P" {
        value 1655;
        description
          "CR5DE2NLFX7P.";
      }
     enum "CR9DLPUFT281" {
        value 1656;
        description
          "CR9DLPUFT281.";
      }
     enum "CX6DSFUIT01B" {
        value 1657;
        description
          "CX6DSFUIT01B.";
      }
     enum "CX6D0SRUA910" {
        value 1658;
        description
          "CX6D0SRUA910.";
      }
     enum "CX6DSFUIT01C" {
        value 1659;
        description
          "CX6DSFUIT01C.";
      }
      enum "CR5D0MPUB772" {
        value 1660;
        description
          "CR5D0MPUB772.";
      }
      enum "CX6D0MPUB772" {
        value 1661;
        description
          "CX6D0MPUB772.";
      }
      enum "TNRD0MPUB770" {
        value 1662;
        description
          "TNRD0MPUB770.";
      }
      enum "CX6D0MPUB710" {
        value 1663;
        description
          "CX6D0MPUB710.";
      }
      enum "ME0D0MPUB770" {
        value 1664;
        description
          "ME0D0MPUB770.";
      }
      enum "CR5DSFUGK070" {
        value 1665;
        description
          "CR5DSFUGK070.";
      }
      enum "CX6DSFUGK070" {
        value 1666;
        description
          "CX6DSFUGK070.";
      }
      enum "TNRDSFUGK070" {
        value 1667;
        description
          "TNRDSFUGK070.";
      }
      enum "CX6DSFUIG010" {
        value 1668;
        description
          "CX6DSFUIG010.";
      }
      enum "ME0DSFUGK070" {
        value 1669;
        description
          "ME0DSFUGK070.";
      }
      enum "CR5D0SRUAB73" {
        value 1670;
        description
          "CR5D0SRUAB73.";
      }
      enum "ME0D0SRUAB70" {
        value 1671;
        description
          "ME0D0SRUAB70.";
      }
      enum "CR5DLPUFT261" {
        value 1672;
        description
          "CR5DLPUFT261.";
      }
      enum "CR5DLPUFT264" {
        value 1673;
        description
          "CR5DLPUFT264.";
      }
      enum "CR5DSFUIT250" {
        value 1674;
        description
          "CR5DSFUIT250.";
      }
      enum "CR5DSFUIT26H" {
        value 1675;
        description
          "CR5DSFUIT26H.";
      }
      enum "CR5D0SRUAC7A" {
        value 1676;
        description
          "CR5D0SRUAC7A.";
      }
      enum "CX6D0SRUAC7A" {
        value 1677;
        description
          "CX6D0SRUAC7A.";
      }
      enum "TNRD0SRUAC70" {
        value 1678;
        description
          "TNRD0SRUAC70.";
      }
      enum "CX6D0SRUAC10" {
        value 1679;
        description
          "CX6D0SRUAC10.";
      }
      enum "ME0D0SRUAC7A" {
        value 1680;
        description
          "ME0D0SRUAC7A.";
      }
      enum "CR5D0SRUAC70" {
        value 1681;
        description
          "CR5D0SRUAC70.";
      }
      enum "CR5D0MPUB870" {
        value 1682;
        description
          "CR5D0MPUB870.";
      }
      enum "CR5DSFUFK070" {
        value 1683;
        description
          "CR5DSFUFK070.";
      }
      enum "CX6D0SFUF870" {
        value 1684;
        description
          "CX6D0SFUF870.";
      }
      enum "TNRDSFUFK070" {
        value 1685;
        description
          "TNRDSFUFK070.";
      }
      enum "CX6DSFUIF070" {
        value 1686;
        description
          "CX6DSFUIF070.";
      }
      enum "ME0DSFUIF070" {
        value 1687;
        description
          "ME0DSFUIF070.";
      }
      enum "CR5D00E4XF25" {
        value 1688;
        description
          "CR5D00E4XF25.";
    }
      enum "CR5DLPUFF170" {
        value 1689;
        description
          "CR5DLPUFF170.";
      }
      enum "CR5DLPUF5270" {
        value 1690;
        description
          "CR5DLPUF5270.";
      }
      enum "CR5DLPUFF17R" {
        value 1691;
        description
          "CR5DLPUFF17R.";
      }
      enum "CR5DEKBEBX7B" {
        value 1692;
        description
          "CR5DEKBEBX7B.";
    }
      enum "CX6DISUFF110" {
    value 1693;
        description
          "CX6DISUFF110.";
      }
      enum "CX6DISUFF11R" {
        value 1694;
        description
          "CX6DISUFF11R.";
      }
      enum "CX6DF1E2NC10" {
        value 1695;
        description
          "CX6DF1E2NC10.";
      }
      enum "CX6DF1E2NB10" {
        value 1696;
        description
          "CX6DF1E2NB10.";
      }
      enum "CX6DF1EFXC10" {
        value 1697;
        description
          "CX6DF1EFXC10.";
      }
      enum "CX6DE1KEBX10" {
        value 1698;
        description
          "CX6DE1KEBX10.";
      }
      enum "CX6DEKBEBX10" {
        value 1699;
        description
          "CX6DEKBEBX10.";
      }
      enum "CX6DF1E2NC1B" {
        value 1700;
        description
          "CX6DF1E2NC1B.";
      }
      enum "CX6DF1E2NB1B" {
        value 1701;
        description
          "CX6DF1E2NB1B.";
      }
      enum "CX6DF1EFXC1B" {
        value 1702;
        description
          "CX6DF1EFXC1B.";
      }
      enum "CX6DE1KEBX1B" {
        value 1703;
        description
          "CX6DE1KEBX1B.";
      }
      enum "CX6DEKBEBX1B" {
        value 1704;
        description
          "CX6DEKBEBX1B.";
      }
      enum "CR5DF1EFXC7P" {
        value 1705;
        description
          "CR5DF1EFXC7P.";
      }
      enum "CR5DLPUFF273" {
        value 1706;
        description
          "CR5DLPUFF273.";
      }
      enum "ANND00CXPA00" {
        value 1707;
        description
          "ANND00CXPA00.";
      }
      enum "ANND000PIU00" {
        value 1708;
        description
          "ANND000PIU00.";
      }
       enum "ANND000PIU01" {
        value 1709;
        description
          "ANND000PIU01.";
      }
       enum "ANND000FAN00" {
        value 1710;
        description
          "ANND000FAN00.";
      }
      enum "CR5DLPUFD07E" {
        value 1711;
        description
          "CR5DLPUFD07E.";
      }
      enum "ME0D0LFXFB70" {
        value 1712;
        description
          "ME0D0LFXFB70.";
      }
      enum "CR5DLPUFF272" {
        value 1713;
        description
          "CR5DLPUFF272.";
      }
      enum "CX6DISUFF210" {
        value 1714;
        description
          "CX6DISUFF210.";
      }
      enum "ME0DBSUFM072" {
        value 1715;
        description
          "ME0DBSUFM072.";
      }
      enum "CR5DSPUIM070" {
        value 1716;
        description
          "CR5DSPUIM070.";
      }
      enum "CR5DF1E2NC70" {
        value 1717;
        description
          "CR5DF1E2NC70.";
      }
      enum "CR5DF1E2NB70" {
        value 1718;
        description
          "CR5DF1E2NB70.";
      }
      enum "CR5DF1EFXC70" {
        value 1719;
        description
          "CR5DF1EFXC70.";
      }
      enum "CR5DE1KEBX70" {
        value 1720;
        description
          "CR5DE1KEBX70.";
      }
      enum "CR5DEKBEBX70" {
        value 1721;
        description
          "CR5DEKBEBX70.";
      }
      enum "CR5DF1E2NC7B" {
        value 1722;
        description
          "CR5DF1E2NC7B.";
      }
      enum "CR5DF1E2NB7B" {
        value 1723;
        description
          "CR5DF1E2NB7B.";
      }
      enum "CR5DF1EFXC7B" {
        value 1724;
        description
          "CR5DF1EFXC7B.";
      }
      enum "CR5DE1KEBX7B" {
        value 1725;
        description
          "CR5DE1KEBX7B.";
      }
     enum "CX6DISUFM012" {
        value 1726;
        description
          "CX6DISUFM012.";
      }
     enum "CX6D00E8NC70" {
        value 1727;
        description
          "CX6D00E8NC70.";
      }
      enum "CR5D00LEXF74" {
        value 1728;
        description
          "CR5D00LEXF74.";
      }
      enum "FAN-F1A-14H24Q" {
        value 1729;
        description
          "FAN-F1A-14H24Q.";
      }
      enum "fname8090NE9000-20-LS" {
        value 1730;
        description
          "NE9000-20-LS Chassis.";
      }
      enum "fname8090NE9000-8-LS" {
        value 1731;
        description
          "NE9000-8-LS Chassis.";
      }
      enum "CR9D0MPUN180-VMPU" {
        value 1732;
        description
          "CR9D0MPUN180-VMPU.";
      }
      enum "CR9D0MPUP180-VMPU" {
        value 1733;
        description
          "CR9D0MPUP180-VMPU.";
      }
      enum "CR5D00LEXF73" {
        value 1734;
        description
          "CR5D00LEXF73.";
      }
      enum "CX6D00LEXF10" {
        value 1735;
        description
          "CX6D00LEXF10.";
      }
      enum "ME0D00LEXF70" {
        value 1736;
        description
          "ME0D00LEXF70.";
      }
      enum "CR5D00LRXF60" {
        value 1737;
        description
          "CR5D00LRXF60.";
      }
      enum "CR5D00EDNB62" {
        value 1738;
        description
          "CR5D00EDNB62.";
      }
      enum "ME0DBSUFT070" {
        value 1739;
        description
          "ME0DBSUFT070.";
      }
      enum "ME0DMSUFT070" {
        value 1740;
        description
          "ME0DMSUFT070.";
      }
      enum "CR5D00E4KC60" {
        value 1741;
        description
          "CR5D00E4KC60.";
      }
      enum "CR5D00LMXF62" {
        value 1742;
        description
          "CR5D00LMXF62.";
      }
      enum "CR5D00E8NB62" {
        value 1743;
        description
          "CR5D00E8NB62.";
      }
      enum "CR5DLPUFT070" {
        value 1744;
        description
          "CR5DLPUFT070.";
      }
      enum "CX6D0MPUB810" {
        value 1745;
        description
          "CX6D0MPUB810.";
      }
      enum "CX6DSFUIT27C" {
        value 1746;
        description
          "CX6DSFUIT27C.";
      }
      enum "CX6D0SRUAG10" {
        value 1747;
        description
          "CX6D0SRUAG10.";
      }
      enum "CX6DSFUIU01F" {
        value 1748;
        description
          "CX6DSFUIU01F.";
      }
      enum "CR5D00E8NB70" {
        value 1749;
        description
          "CR5D00E8NB70.";
      }
      enum "CR5DEDVE8N7P" {
        value 1750;
        description
          "CR5DEDVE8N7P.";
      }
      enum "CR5D00EIYB7P" {
        value 1751;
        description
          "CR5D00EIYB7P.";
      }
      enum "CX6DISUFT010" {
        value 1752;
        description
          "CX6DISUFT010.";
      }
      enum "CR5D00EENB7Q" {
        value 1753;
        description
          "CR5D00EENB7Q.";
      }
      enum "CR5D00EENB73" {
        value 1754;
        description
          "CR5D00EENB73.";
      }
      enum "CX6DLPUFK0A0" {
        value 1755;
        description
          "CX6DLPUFK0A0.";
      }
      enum "CX6D00E4XF25" {
        value 1756;
        description
          "CX6D00E4XF25.";
      }
      enum "CX6D0E5XMF90" {
        value 1757;
        description
          "CX6D0E5XMF90.";
      }
      enum "CX6D00E4XF20" {
        value 1758;
        description
          "CX6D00E4XF20.";
      }
      enum "CX6D00E1NB20" {
        value 1759;
        description
          "CX6D00E1NB20.";
      }
      enum "CX6DE2NE4X12" {
        value 1760;
        description
          "CX6DE2NE4X12.";
      }
      enum "CX6D00E1NC98" {
        value 1761;
        description
          "CX6D00E1NC98.";
      }
      enum "CX6D00LAXF90" {
        value 1762;
        description
          "CX6D00LAXF90.";
      }
      enum "CX6D0L2XFE71" {
        value 1763;
        description
          "CX6D0L2XFE71.";
      }
      enum "CR59T8NBB" {
        value 1764;
        description
          "CR59T8NBB.";
      }
      enum "CR59E2KBA" {
        value 1765;
        description
          "CR59E2KBA.";
      }
      enum "CR59LJXFC" {
        value 1766;
        description
          "CR59LJXFC.";
      }
      enum "CR58E8NBE" {
        value 1767;
        description
          "CR58E8NBE.";
      }
      enum "CR59E8NBE" {
        value 1768;
        description
          "CR59E8NBE.";
      }
      enum "CR59E2KCA1" {
        value 1769;
        description
          "CR59E2KCA1.";
      }
      enum "ME0DL2XEFG7B" {
        value 1770;
        description
          "ME0DL2XEFG7B.";
      }
      enum "ME0DL4XEBG7B" {
        value 1771;
        description
          "ME0DL4XEBG7B.";
      }
      enum "CR5D0LBXFA71" {
        value 1772;
        description
          "CR5D0LBXFA71.";
      }
      enum "CR58E4KE4NB0" {
        value 1773;
        description
          "CR58E4KE4NB0.";
      }
      enum "ME0D0MPUB771" {
        value 1774;
        description
          "ME0D0MPUB771.";
      }
      enum "CR5D0MPUB773" {
        value 1775;
        description
          "CR5D0MPUB773.";
      }
      enum "CR5D0SRUAC7B" {
        value 1776;
        description
          "CR5D0SRUAC7B.";
      }
      enum "ME0D0SRUAC7B" {
        value 1777;
        description
          "ME0D0SRUAC7B.";
      }
      enum "CR5D0SRUAC71" {
        value 1778;
        description
          "CR5D0SRUAC71.";
      }
      enum "CR5D0MPUB871" {
        value 1779;
        description
          "CR5D0MPUB871.";
      }
      enum "CX6D0MPUB871" {
        value 1780;
        description
          "CX6D0MPUB871.";
      }
      enum "CX6D0SRUAC71" {
        value 1781;
        description
          "CX6D0SRUAC71.";
      }
      enum "TNRD0MPUB871" {
        value 1782;
        description
          "TNRD0MPUB871.";
      }
      enum "TNRD0SRUAC71" {
        value 1783;
        description
          "TNRD0SRUAC71.";
      }
      enum "CR5DMPUX8671" {
        value 1784;
        description
          "CR5DMPUX8671.";
      }
      enum "ME0DMPUX8671" {
        value 1785;
        description
          "ME0DMPUX8671.";
      }
      enum "CX6D0E2NBA11" {
        value 1786;
        description
          "CX6D0E2NBA11.";
      }
      enum "CX6D0LAXFA13" {
        value 1787;
        description
          "CX6D0LAXFA13.";
      }
      enum "CR5DEDVE8N70" {
        value 1788;
        description
          "CR5DEDVE8N70.";
      }
      enum "CR5D00EENB72" {
        value 1789;
        description
          "CR5D00EENB72.";
      }
      enum "CR8B0BKP03C0" {
        value 1790;
        description
          "CR8B0BKP03C0.";
      }
      enum "CR8B0BKP03C1" {
        value 1791;
        description
          "CR8B0BKP03C1.";
      }
      enum "CR8B0BKP03C2" {
        value 1792;
        description
          "CR8B0BKP03C2.";
      }
      enum "CR8B0BKP03C3" {
        value 1793;
        description
          "CR8B0BKP03C3.";
      }
      enum "fnameNETENGINE-8000-F1A-8H20Q" {
        value 1794;
        description
          "NETENGINE-8000-F1A-8H20Q chassis.";
      }
      enum "fnameNETENGINE-8000-F1A-8H20Q-AC" {
        value 1795;
        description
          "NETENGINE-8000-F1A-8H20Q-AC chassis.";
      }
      enum "fnameNETENGINE-8000-F1A-8H20Q-DC" {
        value 1796;
        description
          "NETENGINE-8000-F1A-8H20Q-DC chassis.";
      }
      enum "CARD ATN 910C-S" {
        value 1797;
        description
          "CARD ATN 910C-S.";
      }
      enum "CARD ATN 910C-H" {
        value 1798;
        description
          "CARD ATN 910C-H.";
      }
      enum "CX62E8YFA0" {
        value 1799;
        description
          "CX62E8YFA0.";
      }
      enum "CR57LFXFF0" {
        value 1800;
        description
          "CR57LFXFF0.";
      }
      enum "CR57LFXFF1" {
        value 1801;
        description
          "CR57LFXFF1.";
      }
      enum "CR57EKGFB0" {
        value 1802;
        description
          "CR57EKGFB0.";
      }
      enum "CR57EKGFB1" {
        value 1803;
        description
          "CR57EKGFB1.";
      }
      enum "CR57E4VBA0" {
        value 1804;
        description
          "CR57E4VBA0.";
      }
      enum "CR57E4VBA1" {
        value 1805;
        description
          "CR57E4VBA1.";
      }
      enum "CR57E4VBB0" {
        value 1806;
        description
          "CR57E4VBB0.";
      }
      enum "CR57E2NLEXB1" {
        value 1807;
        description
          "CR57E2NLEXB1.";
      }
      enum "NEDD00EV1Q00" {
        value 1808;
        description
          "NEDD00EV1Q00.";
      }
      enum "GPR8CQ20YS" {
        value 1809;
        description
          "GPR8CQ20YS.";
      }
      enum "CX62E2NBD0" {
        value 1810;
        description
          "CX62E2NBD0.";
      }
      enum "CX62E4NBC0" {
        value 1811;
        description
          "CX62E4NBC0.";
      }
      enum "CR57E4NBC0" {
        value 1812;
        description
          "CR57E4NBC0.";
      }
      enum "CR57E4NBC1" {
        value 1813;
        description
          "CR57E4NBC1.";
      }
      enum "ANKD001EV203" {
        value 1814;
        description
          "ANKD001EV203.";
      }
      enum "ANKD001EV204" {
        value 1815;
        description
          "ANKD001EV204.";
      }
      enum "ANKD00EX4S01" {
        value 1816;
        description
          "ANKD00EX4S01.";
      }
      enum "ANKD00EX2S01" {
        value 1817;
        description
          "ANKD00EX2S01.";
      }
      enum "ANDD0EM10F00" {
        value 1818;
        description
          "ANDD0EM10F00.";
      }
      enum "CR57LKXFB1" {
        value 1819;
        description
          "CR57LKXFB1.";
      }
      enum "CR5D0E5XMF94" {
        value 1820;
        description
          "CR5D0E5XMF94.";
      }
      enum "CR5DE2NE4X14" {
        value 1821;
        description
          "CR5DE2NE4X14.";
      }
      enum "CR5D00L4XF91" {
        value 1822;
        description
          "CR5D00L4XF91.";
      }
      enum "CR5D00EAGF96" {
        value 1823;
        description
          "CR5D00EAGF96.";
      }
      enum "CR2D0E5XMF93" {
        value 1824;
        description
          "CR2D0E5XMF93.";
      }
      enum "CR5D00P4CFC1" {
        value 1825;
        description
          "CR5D00P4CFC1.";
      }
      enum "CR5D000DE1C1" {
        value 1826;
        description
          "CR5D000DE1C1.";
      }
      enum "CR5D00C4CFC1" {
        value 1827;
        description
          "CR5D00C4CFC1.";
      }
      enum "ANND16E17500" {
        value 1828;
        description
          "ANND16E17500.";
      }
      enum "ANND00CQ1B00" {
        value 1829;
        description
          "ANND00CQ1B00.";
      }
      enum "CR5D00EAGF95" {
        value 1830;
        description
          "CR5D00EAGF95.";
      }
      enum "CR57E8YFA1" {
        value 1831;
        description
          "CR57E8YFA1.";
      }
      enum "CARD ATN 910C-G" {
        value 1832;
        description
          "CARD ATN 910C-G.";
      }
      enum "fnameNETENGINE-8000-M14-AC" {
        value 1833;
        description
          "NETENGINE-8000-M14-AC chassis.";
      }
      enum "fnameNETENGINE-8000-M14-DC" {
        value 1834;
        description
          "NETENGINE-8000-M14-DC chassis.";
      }
      enum "CR8D0IPU2TC1" {
        value 1835;
        description
          "CR8D0IPU2TC1.";
      }
      enum "CR8D0IPU2TC2" {
        value 1836;
        description
          "CR8D0IPU2TC2.";
      }
      enum "CR8DIPU1T2C3" {
        value 1837;
        description
          "CR8DIPU1T2C3.";
      }
      enum "CR8DIPU1T2C4" {
        value 1838;
        description
          "CR8DIPU1T2C4.";
      }
      enum "CR58EPYFA00" {
        value 1839;
        description
          "CR58EPYFA00.";
      }
      enum "CR59EENBD0" {
        value 1840;
        description
          "CR59EENBD0.";
      }
      enum "CR59LPXFA0" {
        value 1841;
        description
          "CR59LPXFA0.";
      }
      enum "CR5D0IPU2TC1" {
        value 1842;
        description
          "CR5D0IPU2TC1.";
      }
      enum "CR5D0IPU2TC2" {
        value 1843;
        description
          "CR5D0IPU2TC2.";
      }
      enum "CR5DIPU1T2C3" {
        value 1844;
        description
          "CR5DIPU1T2C3.";
      }
      enum "CR5DIPU1T2C4" {
        value 1845;
        description
          "CR5DIPU1T2C4.";
      }
      enum "TNRD0IPU2TC1" {
        value 1846;
        description
          "TNRD0IPU2TC1.";
      }
      enum "TNRDIPU1T2C3" {
        value 1847;
        description
          "TNRDIPU1T2C3.";
      }
      enum "CR5DLPUFT071" {
        value 1848;
        description
          "CR5DLPUFT071.";
      }
      enum "CR5DLPUFT072" {
        value 1849;
        description
          "CR5DLPUFT072.";
      }
      enum "CX6DISUFT011" {
        value 1850;
        description
          "CX6DISUFT011.";
      }
      enum "fnameNE40E-X2-M14-AC" {
        value 1851;
        description
          "NE40E-X2-M14-AC chassis.";
      }
      enum "fnameNE40E-X2-M14-DC" {
        value 1852;
        description
          "NE40E-X2-M14-DC chassis.";
      }
      enum "fnamePTN6900-2-M14-AC" {
        value 1853;
        description
          "PTN6900-2-M14-AC chassis.";
      }
      enum "fnamePTN6900-2-M14-DC" {
        value 1854;
        description
          "PTN6900-2-M14-DC chassis.";
      }
      enum "CR8DIPU1T2C1" {
        value 1855;
        description
          "CR8DIPU1T2C1.";
      }
      enum "CR8DIPU1T2C2" {
        value 1856;
        description
          "CR8DIPU1T2C2.";
      }
      enum "CR8DIPU480C1" {
        value 1857;
        description
          "CR8DIPU480C1.";
      }
      enum "CR8DIPU480C2" {
        value 1858;
        description
          "CR8DIPU480C2.";
      }
      enum "TNRDIPU1T2C1" {
        value 1859;
        description
          "TNRDIPU1T2C1.";
      }
      enum "TNRDIPU480C1" {
        value 1860;
        description
          "TNRDIPU480C1.";
      }
      enum "fnameNETENGINE-8000-M8" {
        value 1861;
        description
          "NETENGINE-8000-M8 chassis.";
      }
      enum "fnameNETENGINE-8000-M8-AC" {
        value 1862;
        description
          "NETENGINE-8000-M8-AC chassis.";
      }
      enum "fnameNETENGINE-8000-M8-DC" {
        value 1863;
        description
          "NETENGINE-8000-M8-DC chassis.";
      }
      enum "fnamePTN6900-2-M8C" {
        value 1864;
        description
          "PTN6900-2-M8C chassis.";
      }
      enum "fnamePTN6900-2-M8C-AC" {
        value 1865;
        description
          "PTN6900-2-M8C-AC chassis.";
      }
      enum "fnamePTN6900-2-M8C-DC" {
        value 1866;
        description
          "PTN6900-2-M8C-DC chassis.";
      }
      enum "ME0DBSUFT072" {
        value 1867;
        description
          "ME0DBSUFT072.";
      }
      enum "ME0DMSUFT073" {
        value 1868;
        description
          "ME0DMSUFT073.";
      }
      enum "ME0DBSUFT074" {
        value 1869;
        description
          "ME0DBSUFT074.";
      }
      enum "ME0DMSUFT075" {
        value 1870;
        description
          "ME0DMSUFT075.";
      }
      enum "GPLI40CQES1" {
        value 1871;
        description
          "GPLI40CQES1.";
      }
      enum "GPLI72YSES1" {
        value 1872;
        description
          "GPLI72YSES1.";
      }
      enum "GPLI8KQ8CQE1" {
        value 1873;
        description
          "GPLI8KQ8CQE1.";
      }
      enum "CR2D00E2NB00" {
        value 1874;
        description
          "CR2D00E2NB00.";
      } 
      enum "CX6DE8VE4N10" {
        value 1875;
        description
          "CX6DE8VE4N10.";
    }
      enum "CARD NetEngine 8000 M1A" {
        value 1876;
        description
          "CARD NetEngine 8000 M1A.";
    }
    	enum "CR5D00E4KB60" {
        value 1877;
        description
          "CR5D00E4KB60.";
    }
	enum "CR5D00NDNC60" {
        value 1878;
        description
          "CR5D00NDNC60.";
    }
	enum "CR5D00LRXF61" {
        value 1879;
        description
          "CR5D00LRXF61.";
    }
	enum "CR5D00EDNB63" {
        value 1880;
        description
          "CR5D00EDNB63.";
    }
	enum "CR5D00E4KB61" {
        value 1881;
        description
          "CR5D00E4KB61.";
    }
	enum "CR5D00NDNC61" {
        value 1882;
        description
          "CR5D00NDNC61.";
    }
    enum "CR9D00EPYF8P" {
        value 1883;
        description
          "CR9D00EPYF8P.";
    }
	enum "CR5D0MPUQ1D1" {
        value 1884;
        description
          "CR5D0MPUQ1D1.";
    }
	enum "CR5D0MPUQ1D0" {
        value 1885;
        description
          "CR5D0MPUQ1D0.";
    }
	enum "CR9D0MPUQ180" {
        value 1886;
        description
          "CR9D0MPUQ180.";
    }
	enum "CR9D0MPUR180" {
        value 1887;
        description
          "CR9D0MPUR180.";
    }
	enum "CR5D0SFUT2D1" {
        value 1888;
        description
          "CR5D0SFUT2D1.";
    }
	enum "CR5D0SFUT2D2" {
        value 1889;
        description
          "CR5D0SFUT2D2.";
    }
	enum "CR5D00EENBD0" {
        value 1890;
        description
          "CR5D00EENBD0.";
    }
	enum "CR5D00EENBD1" {
        value 1891;
        description
          "CR5D00EENBD1.";
    }
	enum "CR5D00EPXFD1" {
        value 1892;
        description
          "CR5D00EPXFD1.";
    }
	enum "CR5D00EPXFD0" {
        value 1893;
        description
          "CR5D00EPXFD0.";
    }
      enum "CR5D0MPUB661" {
        value 1894;
        description
          "CR5D0MPUB661.";
      }	
    enum "CX62E2NBB00" {
        value 1895;
        description
          "CX62E2NBB00.";
      }
     enum "CX62LEXFC00" {
        value 1896;
        description
          "CX62LEXFC00.";
      }
     enum "CR5DE8VE4N70" {
        value 1897;
        description
          "CR5DE8VE4N70.";
      }
     enum "ANND0EM10F00" {
        value 1898;
        description
          "ANND0EM10F00.";
      }
     enum "ANND0EM20F00" {
        value 1899;
        description
          "ANND0EM20F00.";
      }
     enum "CR5D00EEGF73" {
        value 1900;
        description
          "CR5D00EEGF73.";
      }
      enum "CR5D00E1NC97" {
        value 1901;
        description
          "CR5D00E1NC97.";
      }
    enum "GPLI40CQE2" {
        value 1902;
        description
          "GPLI40CQE2.";
      }
    enum "GPLI72YSE2" {
        value 1903;
        description
          "GPLI72YSE2.";
      }
      enum "CR5D00C8CF72" {
        value 1904;
        description
          "CR5D00C8CF72.";
      }
      enum "CR5D00P8CF70" {
        value 1905;
        description
          "CR5D00P8CF70.";
      }
      enum "CR5D00CFE170" {
        value 1906;
        description
          "CR5D00CFE170.";
      }
     enum "CR5D0MPUA850" {
        value 1907;
        description
          "CR5D0MPUA850.";
      }
     enum "CR5D0MPUA851" {
        value 1908;
        description
          "CR5D0MPUA851.";
      }
    enum "CR5DVSUIK071" {
        value 1909;
        description
          "CR5DVSUIK071.";
    }
    enum "CR5DVSUIK073" {
        value 1910;
        description
          "CR5DVSUIK073.";
    }
    enum "ME0DVSUIK071" {
        value 1911;
        description
          "ME0DVSUIK071.";
    }
    enum "ME0DVSUIK073" {
        value 1912;
        description
          "ME0DVSUIK073.";
    }
    enum "CR5DVSUIK070" {
        value 1913;
        description
          "CR5DVSUIK070.";
    }
    enum "CR5DVSUIK072" {
        value 1914;
        description
          "CR5DVSUIK072.";
    }
    enum "CR5DJYSUK072" {
        value 1915;
        description
          "CR5DJYSUK072.";
    }
    enum "ME0DVSUIK070" {
        value 1916;
        description
          "ME0DVSUIK070.";
    }
    enum "ME0DVSUIK072" {
        value 1917;
        description
          "ME0DVSUIK072.";
    }
    enum "ME0DJYSUK070" {
        value 1918;
        description
          "ME0DJYSUK070.";
    }
    enum "fnameNETENGINE-8000-X8-HVDC" {
        value 1919;
        description
          "NETENGINE-8000-X8-HVDC chassis.";
    }
    enum "fnameNETENGINE-8000-X8-DC" {
        value 1920;
        description
          "NETENGINE-8000-X8-DC chassis.";
    }
    enum "CR8D0MPUA1C0" {
        value 1921;
        description
          "CR8D0MPUA1C0.";
    }
    enum "CR8D0MPUA1C1" {
        value 1922;
        description
          "CR8D0MPUA1C1.";
    }
    enum "CR8DSFUI4TC1" {
        value 1923;
        description
          "CR8DSFUI4TC1.";
    }
    enum "CR8DSFUI4TC3" {
        value 1924;
        description
          "CR8DSFUI4TC3.";
    }
    enum "CR8DSFUI4TC0" {
        value 1925;
        description
          "CR8DSFUI4TC0.";
    }
    enum "CR8DSFUI4TC2" {
        value 1926;
        description
          "CR8DSFUI4TC2.";
    }
    enum "CR8D00EKNBCP" {
        value 1927;
        description
          "CR8D00EKNBCP.";
    }
    enum "CR8D00EKNBCR" {
        value 1928;
        description
          "CR8D00EKNBCR.";
    }
    enum "CR8D00EKNBCQ" {
        value 1929;
        description
          "CR8D00EKNBCQ.";
    }
    enum "CR8D00EKNBC0" {
        value 1930;
        description
          "CR8D00EKNBC0.";
    }
    enum "CR8D00LRXFCP" {
        value 1931;
        description
          "CR8D00LRXFCP.";
    }
    enum "CR8D00LRXFCR" {
        value 1932;
        description
          "CR8D00LRXFCR.";
    }
    enum "CR8D00LRXFCQ" {
        value 1933;
        description
          "CR8D00LRXFCQ.";
    }
    enum "CR8D00LRXFC0" {
        value 1934;
        description
          "CR8D00LRXFC0.";
    }
    enum "CR8D00E1VBC0" {
        value 1935;
        description
          "CR8D00E1VBC0.";
     }
      enum "CR8D25E2XFC0" {
        value 1936;
        description
          "CR8D25E2XFC0.";
      }
      enum "CR8D00L4XFC0" {
        value 1937;
        description
          "CR8D00L4XFC0.";
      }
      enum "CR8D00E2XFC0" {
        value 1938;
        description
          "CR8D00E2XFC0.";
      }
      enum "CR8D00EAGFC0" {
        value 1939;
        description
          "CR8D00EAGFC0.";
      }
      enum "CR8D00EEGFC0" {
        value 1940;
        description
          "CR8D00EEGFC0.";
      }
    enum "CR5DSFUIT27M" {
        value 1941;
        description
          "CR5DSFUIT27M.";
          }
    enum "CR5DSFUIT27N" {
        value 1942;
        description
          "CR5DSFUIT27N.";
          }
    enum "CR5DSFUIT27K" {
        value 1943;
        description
          "CR5DSFUIT27K.";
          }
    enum "CR5DSFUIT27L" {
        value 1944;
        description
          "CR5DSFUIT27L.";
          }
    enum "CX6DSFUIT27F" {
        value 1945;
        description
          "CX6DSFUIT27F.";
          }
    enum "CX6DSFUIU07G" {
        value 1946;
        description
          "CX6DSFUIU07G.";
          }
    enum "TNRDSFUIT27G" {
        value 1947;
        description
          "TNRDSFUIT27G.";
          }
    enum "TNRDSFUIU07H" {
        value 1948;
        description
          "TNRDSFUIU07H.";
          }
    enum "ME0DSFUIT07E" {
        value 1949;
        description
          "ME0DSFUIT07E.";
          }
    enum "ME0DSFUIT17E" {
        value 1950;
        description
          "ME0DSFUIT17E.";
          }
    enum "ME0DSFUIT07F" {
        value 1951;
        description
          "ME0DSFUIT07F.";
          }
    enum "ME0DSFUIT17F" {
        value 1952;
        description
          "ME0DSFUIT17F.";
          }
    enum "CR5D0MPUB970" {
        value 1953;
        description
          "CR5D0MPUB970.";
          }
    enum "CR5D0MPUB971" {
        value 1954;
        description
          "CR5D0MPUB971.";
          }
    enum "CX6D0MPUB970" {
        value 1955;
        description
          "CX6D0MPUB970.";
          }
    enum "CX6D0MPUB910" {
        value 1956;
        description
          "CX6D0MPUB910.";
          }
    enum "ME0DMPUX8970" {
        value 1957;
        description
          "ME0DMPUX8970.";
          }
    enum "ME0DMPUX8971" {
        value 1958;
        description
          "ME0DMPUX8971.";
          }
    enum "TNRD0MPUB970" {
        value 1959;
        description
          "TNRD0MPUB970.";
          }
    enum "CR5D0SRUAD70" {
        value 1960;
        description
          "CR5D0SRUAD70.";
          }
    enum "CR5D0SRUAD71" {
        value 1961;
        description
          "CR5D0SRUAD71.";
          }
    enum "CX6D0SRUAD70" {
        value 1962;
        description
          "CX6D0SRUAD70.";
          }
    enum "TNRD0SRUAD70" {
        value 1963;
        description
          "TNRD0SRUAD70.";
          }
    enum "CR5D0SRUAE70" {
        value 1964;
        description
          "CR5D0SRUAE70.";
          }
    enum "CR5D0SRUAE71" {
        value 1965;
        description
          "CR5D0SRUAE71.";
          }
    enum "CX6D0SRUAE70" {
        value 1966;
        description
          "CX6D0SRUAE70.";
          }
    enum "CX6D0SRUAE10" {
        value 1967;
        description
          "CX6D0SRUAE10.";
          }
    enum "ME0D0SRUAD71" {
        value 1968;
        description
          "ME0D0SRUAD71.";
          }
    enum "ME0D0SRUAD70" {
        value 1969;
        description
          "ME0D0SRUAD70.";
          }
    enum "TNRD0SRUAE70" {
        value 1970;
        description
          "TNRD0SRUAE70.";
          }
    enum "fnameNETENGINE-8000-X4-HVDC" {
        value 1971;
        description
          "NETENGINE-8000-X4-HVDC chassis.";
    }
    enum "fnameNETENGINE-8000-X4-DC" {
        value 1972;
        description
          "NETENGINE-8000-X4-DC chassis.";
    }
    enum "CR5D00ICUC51" {
        value 1973;
        description
          "CR5D00ICUC51.";
    }
    enum "CR5D00ICUC52" {
        value 1974;
        description
          "CR5D00ICUC52.";
    }
    enum "ANRD00CXPA00" {
        value 2014;
        description
          "ANRD00CXPA00.";
      }
      enum "ANRD00CXPA01" {
        value 2015;
        description
          "ANRD00CXPA01.";
      }
      enum "ANRD01CXPA00" {
        value 2016;
        description
          "ANRD01CXPA00.";
      }
      enum "ANRD01CXPB00" {
        value 2017;
        description
          "ANRD01CXPB00.";
      }
      enum "CR8DCXP160C0" {
        value 2018;
        description
          "CR8DCXP160C0.";
      }
      enum "CR8DCXP160C1" {
        value 2019;
        description
          "CR8DCXP160C1.";
      }
      enum "CR8DCXP160C2" {
        value 2020;
        description
          "CR8DCXP160C2.";
      }
      enum "CR8DCXP160C3" {
        value 2021;
        description
          "CR8DCXP160C3.";
      }
      enum "CR5D00EDNB64" {
        value 2022;
        description
          "CR5D00EDNB64.";
    }
    enum "CR58EENBD1" {
        value 2035;
        description
          "CR58EENBD1.";
      }
    enum "ATN950D-AC" {
        value 2036;
        description
          "ATN950D-AC chassis.";
      }
    enum "ATN950D-DC" {
        value 2037;
        description
          "ATN950D-DC chassis.";
      }
    enum "fnameNETENGINE-8000-M6-AC" {
        value 2038;
        description
          "NETENGINE-8000-M6-AC chassis.";
      }
    enum "fnameNETENGINE-8000-M6-DC" {
        value 2039;
        description
          "NETENGINE-8000-M6-DC chassis.";
      }
    enum "CR9P9KHALM8B" {
        value 2040;
        description
          "CR9P9KHALM8B.";
    }
    enum "CR8DIPU240C1" {
        value 2041;
        description
          "CR8DIPU240C1.";
    }
    enum "CR8DIPU240C2" {
        value 2042;
        description
          "CR8DIPU240C2.";
    }
    enum "CR8D00E1NBC1" {
        value 2043;
        description
          "CR8D00E1NBC1.";
    }
    enum "CR8D00E2VBC1" {
        value 2044;
        description
          "CR8D00E2VBC1.";
    }
    enum "CR8D00E2NBC1" {
        value 2045;
        description
          "CR8D00E2NBC1.";
      }
    enum "CR9D0MPUR181" {
        value 2055;
        description
          "CR9D0MPUR181.";
      }
    enum "CR9D0SFUT48G" {
        value 2056;
        description
          "CR9D0SFUT48G.";
      }
    enum "CR5D00E4KB62" {
        value 2063;
        description
          "CR5D00E4KB62.";
    }
    enum "CR5D00LRXF62" {
        value 2064;
        description
          "CR5D00LRXF62.";
    }
    enum "CR5DSFUIT076" {
        value 2095;
        description
          "CR5DSFUIT076.";
      }
    enum "CR5DSFUIT077" {
        value 2096;
        description
          "CR5DSFUIT077.";
      }
    enum "CX6DSFUIT072" {
        value 2097;
        description
          "CX6DSFUIT072.";
      }
    enum "TNRDSFUIT072" {
        value 2098;
        description
          "TNRDSFUIT072.";
      }
    enum "CX6DSFUIT27J" {
        value 2099;
        description
          "CX6DSFUIT27J.";
      }
    enum "CR5DSFUIT078" {
        value 2100;
        description
          "CR5DSFUIT078.";
      }
    enum "CR5DSFUIT079" {
        value 2101;
        description
          "CR5DSFUIT079.";
      }
    enum "CX6DSFUIT073" {
        value 2102;
        description
          "CX6DSFUIT073.";
      }
    enum "TNRDSFUIT073" {
        value 2103;
        description
          "TNRDSFUIT073.";
      }
    enum "CX6DSFUIT21H" {
        value 2104;
        description
          "CX6DSFUIT21H.";
    }
    enum "CR5D0SRUAC76" {
      value 2114;
      description
        "CR5D0SRUAC76.";
    }
    }
    description
      "Hardware-hard-type.";
  }
  typedef hardware-cardhard-type {
    type enumeration {
      enum "unknown" {
        value 0;
        description
          "Unknown card.";
      }
      enum "LAN_WAN_36x10GF_CARD" {
        value 1;
        description
          "LAN_WAN_36x10GF_CARD.";
      }
      enum "ETH_20xGF_T_CARD" {
        value 2;
        description
          "ETH_20xGF_T_CARD.";
      }
      enum "ETH_2x10G_10GF_B_CARD" {
        value 3;
        description
          "ETH_2x10G_10GF_B_CARD.";
      }
      enum "ETH_1x10G_11GF_B_CARD" {
        value 4;
        description
          "ETH_1x10G_11GF_B_CARD.";
      }
      enum "FLEX_POS_10G_CARD" {
        value 5;
        description
          "FLEX_POS_10G_CARD.";
      }
      enum "FLEX_POS_2X2.5G_CARD" {
        value 6;
        description
          "FLEX_POS_2X2.5G_CARD.";
      }
      enum "FLEX_POS_4X2.5G_CARD" {
        value 7;
        description
          "FLEX_POS_4X2.5G_CARD.";
      }
      enum "FLEX_POS_4X622M_CARD" {
        value 8;
        description
          "FLEX_POS_4X622M_CARD.";
      }
      enum "FLEX_POS_8X622M_CARD" {
        value 9;
        description
          "FLEX_POS_8X622M_CARD.";
      }
      enum "ETH_3x40GC_B_CARD" {
        value 10;
        description
          "ETH_3x40GC_B_CARD.";
      }
      enum "POS_2x10GX_CARD" {
        value 11;
        description
          "POS_2x10GX_CARD.";
      }
      enum "ETH_4x10G_12GF_B_CARD" {
        value 12;
        description
          "ETH_4x10G_12GF_B_CARD.";
      }
      enum "OTN_1x40GC_CARD" {
        value 13;
        description
          "OTN_1x40GC_CARD.";
      }
      enum "OTN_12x10GF_CARD" {
        value 14;
        description
          "OTN_12x10GF_CARD.";
      }
      enum "OTN_6x10GF_CARD" {
        value 15;
        description
          "OTN_6x10GF_CARD.";
      }
      enum "FLEX_24XCE1CT1_CARD" {
        value 16;
        description
          "FLEX_24XCE1CT1_CARD.";
      }
      enum "FLEX_2XCPOS_CARD" {
        value 17;
        description
          "FLEX_2XCPOS_CARD.";
      }
      enum "FLEX_4XCPOS_CARD" {
        value 18;
        description
          "FLEX_4XCPOS_CARD.";
      }
      enum "FLEX_8XCPOS_CARD" {
        value 19;
        description
          "FLEX_8XCPOS_CARD.";
      }
      enum "LAN_WAN_2x10GF_T_CARD" {
        value 20;
        description
          "LAN_WAN_2x10GF_T_CARD.";
      }
      enum "LAN_WAN_5x10GF_T_CARD" {
        value 21;
        description
          "LAN_WAN_5x10GF_T_CARD.";
      }
      enum "ETH_24xGF_T_CARD" {
        value 22;
        description
          "ETH_24xGF_T_CARD.";
      }
      enum "ETH_12xGF_T_CARD" {
        value 23;
        description
          "ETH_12xGF_T_CARD.";
      }
      enum "ETH_2x50GE_4x25GE_8x10GE_8xGE" {
        value 24;
        description
          "ETH_2x50GE_4x25GE_8x10GE_8xGE.";
      }
      enum "ETH_48xGF_B_CARD" {
        value 25;
        description
          "ETH_48xGF_B_CARD.";
      }
      enum "ETH_2x10G_32GF_B_CARD" {
        value 26;
        description
          "ETH_2x10G_32GF_B_CARD.";
      }
      enum "FLEX_ETH_8XGF_B_CARD" {
        value 27;
        description
          "FLEX_ETH_8XGF_B_CARD.";
      }
      enum "ETH_LAN_WAN_2X10G_CARD" {
        value 28;
        description
          "ETH_LAN_WAN_2X10G_CARD.";
      }
      enum "ETH_1x10G_16GF_B_CARD" {
        value 29;
        description
          "ETH_1x10G_16GF_B_CARD.";
      }
      enum "FLEX_POS_8X155M_CARD" {
        value 30;
        description
          "FLEX_POS_8X155M_CARD.";
      }
      enum "FLEX_POS_4X155M_CARD" {
        value 31;
        description
          "FLEX_POS_4X155M_CARD.";
      }
      enum "FLEX_POS_2X155M_CARD" {
        value 32;
        description
          "FLEX_POS_2X155M_CARD.";
      }
      enum "ETH_20xGE_B_CARD" {
        value 33;
        description
          "ETH_20xGE_B_CARD.";
      }
      enum "ETH_20xGE_CARD" {
        value 34;
        description
          "ETH_20xGE_CARD.";
      }
      enum "LAN_2x10GF_ETH_24xGF_CARD" {
        value 35;
        description
          "LAN_2x10GF_ETH_24xGF_CARD.";
      }
      enum "LAN_4x10GF_ETH_40xGF_CARD" {
        value 36;
        description
          "LAN_4x10GF_ETH_40xGF_CARD.";
      }
      enum "ETH_4x50GB_CARD" {
        value 37;
        description
          "ETH_4x50GB_CARD.";
      }
      enum "ETH_40xGF_CARD" {
        value 38;
        description
          "ETH_40xGF_CARD.";
      }
      enum "ETH_4xFE_B_2xAUX_CARD" {
        value 39;
        description
          "ETH_4xFE_B_2xAUX_CARD.";
      }
      enum "LAN_WAN_2x10GXC_CARD" {
        value 40;
        description
          "LAN_WAN_2x10GXC_CARD.";
      }
      enum "ETH_8xGED_CARD" {
        value 41;
        description
          "ETH_8xGED_CARD.";
      }
      enum "LAN_10GF_ETH_8xGFB_CARD" {
        value 42;
        description
          "LAN_10GF_ETH_8xGFB_CARD.";
      }
      enum "LAN_WAN_4x10GXD_CARD" {
        value 43;
        description
          "LAN_WAN_4x10GXD_CARD.";
      }
      enum "ETH_10xGFD_CARD" {
        value 44;
        description
          "ETH_10xGFD_CARD.";
      }
      enum "ETH_10G_WAN" {
        value 45;
        description
          "ETH_10G_WAN.";
      }
      enum "ETH_10G_LAN" {
        value 46;
        description
          "ETH_10G_LAN.";
      }
      enum "ETH_8x100G_CARD" {
        value 47;
        description
          "ETH_8x100G_CARD.";
      }
      enum "ETH_24x40G_CARD" {
        value 48;
        description
          "ETH_24x40G_CARD.";
      }
      enum "LAN_WAN_60x10GF_CARD" {
        value 49;
        description
          "LAN_WAN_60x10GF_CARD.";
      }
      enum "ETH_10XGE_CARD" {
        value 50;
        description
          "ETH_10XGE_CARD.";
      }
      enum "ETH_10xGE" {
        value 51;
        description
          "ETH_10xGE.";
      }
      enum "POS_4X2.5G_CARD" {
        value 52;
        description
          "POS_4X2.5G_CARD.";
      }
      enum "POS_1X10G_CARD" {
        value 53;
        description
          "POS_1X10G_CARD.";
      }
      enum "POS_4X622M_CARD" {
        value 54;
        description
          "POS_4X622M_CARD.";
      }
      enum "ETH_2X10G_LAN_CARD" {
        value 55;
        description
          "ETH_2X10G_LAN_CARD.";
      }
      enum "ETH_2X10G_WAN_CARD" {
        value 56;
        description
          "ETH_2X10G_WAN_CARD.";
      }
      enum "ETH_48XGE_CARD" {
        value 57;
        description
          "ETH_48XGE_CARD.";
      }
      enum "POS_8X155M_CARD" {
        value 58;
        description
          "POS_8X155M_CARD.";
      }
      enum "ETH_24XGE_CARD" {
        value 59;
        description
          "ETH_24XGE_CARD.";
      }
      enum "POS_1X2.5G_CARD" {
        value 60;
        description
          "POS_1X2.5G_CARD.";
      }
      enum "POS_2X2.5G_CARD" {
        value 61;
        description
          "POS_2X2.5G_CARD.";
      }
      enum "POS_2X10G_CARD" {
        value 62;
        description
          "POS_2X10G_CARD.";
      }
      enum "POS_4X155M_CARD" {
        value 63;
        description
          "POS_4X155M_CARD.";
      }
      enum "ETH_5XGE_CARD" {
        value 64;
        description
          "ETH_5XGE_CARD.";
      }
      enum "P1MZ_CARD" {
        value 65;
        description
          "P1MZ_CARD.";
      }
      enum "D1MV_CARD" {
        value 66;
        description
          "D1MV_CARD.";
      }
      enum "ETH_LAN_WAN_4X10G_CARD" {
        value 67;
        description
          "ETH_LAN_WAN_4X10G_CARD.";
      }
      enum "LAN_WAN_2x10GX_CARD" {
        value 68;
        description
          "LAN_WAN_2x10GX_CARD.";
      }
      enum "ETH_2x10GX_CARD" {
        value 69;
        description
          "ETH_2x10GX_CARD.";
      }
      enum "OTN_2x10GX_CARD" {
        value 70;
        description
          "OTN_2x10GX_CARD.";
      }
      enum "LAN_WAN_5x10GX_CARD" {
        value 71;
        description
          "LAN_WAN_5x10GX_CARD.";
      }
      enum "ETH_5x10GX_CARD" {
        value 72;
        description
          "ETH_5x10GX_CARD.";
      }
      enum "POS_40GZ_CARD" {
        value 73;
        description
          "POS_40GZ_CARD.";
      }
      enum "ETH_24xGF_CARD" {
        value 74;
        description
          "ETH_24xGF_CARD.";
      }
      enum "OFCA_CARD" {
        value 75;
        description
          "OFCA_CARD.";
      }
      enum "OFCV_CARD" {
        value 76;
        description
          "OFCV_CARD.";
      }
      enum "OFC40_CARD" {
        value 77;
        description
          "OFC40_CARD.";
      }
      enum "OFC100B_CARD" {
        value 78;
        description
          "OFC100B_CARD.";
      }
      enum "OFC400A_CARD" {
        value 79;
        description
          "OFC400A_CARD.";
      }
      enum "OFC1TA_CARD" {
        value 80;
        description
          "OFC1TA_CARD.";
      }
      enum "OFC400B_CARD" {
        value 81;
        description
          "OFC400B_CARD.";
      }
      enum "OFC1TB_CARD" {
        value 82;
        description
          "OFC1TB_CARD.";
      }
      enum "OFC2TB_CARD" {
        value 83;
        description
          "OFC2TB_CARD.";
      }
      enum "OFC2TA_CARD" {
        value 84;
        description
          "OFC2TA_CARD.";
      }
      enum "OFC1TC_CARD" {
        value 85;
        description
          "OFC1TC_CARD.";
      }
      enum "OFC1TD_CARD" {
        value 86;
        description
          "OFC1TD_CARD.";
      }
      enum "OFC400D_CARD" {
        value 87;
        description
          "OFC400D_CARD.";
      }
      enum "OFC100A_CARD" {
        value 88;
        description
          "OFC100A_CARD.";
      }
      enum "OFCB_CARD" {
        value 89;
        description
          "OFCB_CARD.";
      }
      enum "POS_10G_CARD" {
        value 90;
        description
          "POS_10G_CARD.";
      }
      enum "POS_40G_CARD" {
        value 91;
        description
          "POS_40G_CARD.";
      }
      enum "WDM_40G_CARD" {
        value 92;
        description
          "WDM_40G_CARD.";
      }
      enum "ETH_40XGE_SFP_CARD" {
        value 93;
        description
          "ETH_40XGE_SFP_CARD.";
      }
      enum "ETH_40GC_CARD" {
        value 94;
        description
          "ETH_40GC_CARD.";
      }
      enum "ETH_2x100GC_CARD" {
        value 95;
        description
          "ETH_2x100GC_CARD.";
      }
      enum "ETH_100GC_T_CARD" {
        value 96;
        description
          "ETH_100GC_T_CARD.";
      }
      enum "LAN_WAN_20x10GX_CARD" {
        value 97;
        description
          "LAN_WAN_20x10GX_CARD.";
      }
      enum "ETH_10x100GF_CARD" {
        value 98;
        description
          "ETH_10x100GF_CARD.";
      }
      enum "ETH_6x40GC_CARD" {
        value 99;
        description
          "ETH_6x40GC_CARD.";
      }
      enum "ETH_1x100GC_CARD" {
        value 100;
        description
          "ETH_1x100GC_CARD.";
      }
      enum "LAN_WAN_24x10GX_CARD" {
        value 101;
        description
          "LAN_WAN_24x10GX_CARD.";
      }
      enum "LAN_WAN_5x10GXB_CARD" {
        value 102;
        description
          "LAN_WAN_5x10GXB_CARD.";
      }
      enum "ETH_5x10GXB_CARD" {
        value 103;
        description
          "ETH_5x10GXB_CARD.";
      }
      enum "POS_8x2.5G_CARD" {
        value 104;
        description
          "POS_8x2.5G_CARD.";
      }
      enum "FLEX_1xCPOS_CARD" {
        value 105;
        description
          "FLEX_1xCPOS_CARD.";
      }
      enum "ETH_5x40GC_CARD" {
        value 106;
        description
          "ETH_5x40GC_CARD.";
      }
      enum "SPU" {
        value 107;
        description
          "SPU.";
      }
      enum "TSUA" {
        value 108;
        description
          "TSUA.";
      }
      enum "LAN_WAN_10x10GX_CARD" {
        value 109;
        description
          "LAN_WAN_10x10GX_CARD.";
      }
      enum "ETH_8xGFC_CARD" {
        value 110;
        description
          "ETH_8xGFC_CARD.";
      }
      enum "ETH_8xGE_CARD" {
        value 111;
        description
          "ETH_8xGE_CARD.";
      }
      enum "FLEX_4xCPOS_CARD" {
        value 112;
        description
          "FLEX_4xCPOS_CARD.";
      }
      enum "FLEX_32xMIE1_CARD" {
        value 113;
        description
          "FLEX_32xMIE1_CARD.";
      }
      enum "FLEX_32xMIE1B_CARD" {
        value 114;
        description
          "FLEX_32xMIE1B_CARD.";
      }
      enum "FLEX_16xMDE1A_CARD" {
        value 115;
        description
          "FLEX_16xMDE1A_CARD.";
      }
      enum "FLEX_16xMDE1B_CARD" {
        value 116;
        description
          "FLEX_16xMDE1B_CARD.";
      }
      enum "POS_4x155MFA_CARD" {
        value 117;
        description
          "POS_4x155MFA_CARD.";
      }
      enum "LAN_WAN_4x10GF_CARD" {
        value 118;
        description
          "LAN_WAN_4x10GF_CARD.";
      }
      enum "ETH_4x10GF_CARD" {
        value 119;
        description
          "ETH_4x10GF_CARD.";
      }
      enum "LAN_10GF_ETH_8xGF_CARD" {
        value 120;
        description
          "LAN_10GF_ETH_8xGF_CARD.";
      }
      enum "ETH_24xGF_B_CARD" {
        value 121;
        description
          "ETH_24xGF_B_CARD.";
      }
      enum "LAN_WAN_12x10GF_B_CARD" {
        value 122;
        description
          "LAN_WAN_12x10GF_B_CARD.";
      }
      enum "ETH_1x100GC_B_CARD" {
        value 123;
        description
          "ETH_1x100GC_B_CARD.";
      }
      enum "LAN_WAN_10x10GF_B_CARD" {
        value 124;
        description
          "LAN_WAN_10x10GF_B_CARD.";
      }
      enum "WDM_2x100GC_CARD" {
        value 125;
        description
          "WDM_2x100GC_CARD.";
      }
      enum "ETH_1x40GC_B_CARD" {
        value 126;
        description
          "ETH_1x40GC_B_CARD.";
      }
      enum "LAN_WAN_6x10GF_B_CARD" {
        value 127;
        description
          "LAN_WAN_6x10GF_B_CARD.";
      }
      enum "LAN_WAN_5x10GF_B_CARD" {
        value 128;
        description
          "LAN_WAN_5x10GF_B_CARD.";
      }
      enum "LAN_WAN_4x10GF_B_CARD" {
        value 129;
        description
          "LAN_WAN_4x10GF_B_CARD.";
      }
      enum "LAN_WAN_3x10GF_B_CARD" {
        value 130;
        description
          "LAN_WAN_3x10GF_B_CARD.";
      }
      enum "ADM" {
        value 131;
        description
          "ADM.";
      }
      enum "ETH_24x40GC_CARD" {
        value 132;
        description
          "ETH_24x40GC_CARD.";
      }
      enum "OFC400C_CARD" {
        value 133;
        description
          "OFC400C_CARD.";
      }
      enum "FLEX_4xE3CT3_CARD" {
        value 134;
        description
          "FLEX_4xE3CT3_CARD.";
      }
      enum "ETH_2x100GC_T_CARD" {
        value 135;
        description
          "ETH_2x100GC_T_CARD.";
      }
      enum "LAN_WAN_24x10GF_T_CARD" {
        value 136;
        description
          "LAN_WAN_24x10GF_T_CARD.";
      }
      enum "LAN_WAN_2x10GF_B_CARD" {
        value 137;
        description
          "LAN_WAN_2x10GF_B_CARD.";
      }
      enum "POS_4x155MF_CARD" {
        value 138;
        description
          "POS_4x155MF_CARD.";
      }
      enum "POS_2x622MF_CARD" {
        value 139;
        description
          "POS_2x622MF_CARD.";
      }
      enum "POS_2x155MF_CARD" {
        value 140;
        description
          "POS_2x155MF_CARD.";
      }
      enum "POS_622MF_CARD" {
        value 141;
        description
          "POS_622MF_CARD.";
      }
      enum "DVSU_SP_CARD" {
        value 142;
        description
          "DVSU_SP_CARD.";
      }
      enum "OTN_4x10GF_CARD" {
        value 143;
        description
          "OTN_4x10GF_CARD.";
      }
      enum "OTN_2x100GF_CARD" {
        value 144;
        description
          "OTN_2x100GF_CARD.";
      }
      enum "ETH_10x100GF_A_CARD" {
        value 145;
        description
          "ETH_10x100GF_A_CARD.";
      }
      enum "OTN_1x100GF_CARD" {
        value 146;
        description
          "OTN_1x100GF_CARD.";
      }
      enum "LAN_WAN_10x10GF_T_CARD" {
        value 147;
        description
          "LAN_WAN_10x10GF_T_CARD.";
      }
      enum "FLEX_ATM_2x155M_CARD" {
        value 148;
        description
          "FLEX_ATM_2x155M_CARD.";
      }
      enum "ETH_8x100GC_CARD" {
        value 149;
        description
          "ETH_8x100GC_CARD.";
      }
      enum "ETH_8x100GF_LW_16x10GF" {
        value 150;
        description
          "ETH_8x100GF_LW_16x10GF.";
      }
      enum "ETH_16x100GF_CARD" {
        value 151;
        description
          "ETH_16x100GF_CARD.";
      }
      enum "ETH_16x100GF_LW_32x10GF" {
        value 152;
        description
          "ETH_16x100GF_LW_32x10GF.";
      }
      enum "ETH_10xGF_T_CARD" {
        value 153;
        description
          "ETH_10xGF_T_CARD.";
      }
      enum "LAN_WAN_5x10GF_H_CARD" {
        value 154;
        description
          "LAN_WAN_5x10GF_H_CARD.";
      }
      enum "LAN_WAN_2x10GF_H_CARD" {
        value 155;
        description
          "LAN_WAN_2x10GF_H_CARD.";
      }
      enum "LAN_WAN_2x10GF_I_CARD" {
        value 156;
        description
          "LAN_WAN_2x10GF_I_CARD.";
      }
      enum "LAN_WAN_5x10GF_I_CARD" {
        value 157;
        description
          "LAN_WAN_5x10GF_I_CARD.";
      }
      enum "ETH_2x100GB_CARD" {
        value 158;
        description
          "ETH_2x100GB_CARD.";
      }
      enum "ETH_4x100GB_CARD" {
        value 159;
        description
          "ETH_4x100GB_CARD.";
      }
      enum "ETH_40x10GF_CARD" {
        value 160;
        description
          "ETH_40x10GF_CARD.";
      }
      enum "LAN_WAN_40x10GF_CARD" {
        value 161;
        description
          "LAN_WAN_40x10GF_CARD.";
      }
      enum "ETH_10x10GE" {
        value 162;
        description
          "ETH_10x10GE.";
      }
      enum "OTN_4x10GX" {
        value 163;
        description
          "OTN_4x10GX.";
      }
      enum "ETH_1x100GE" {
        value 164;
        description
          "ETH_1x100GE.";
      }
      enum "ETH_1x50GE" {
        value 165;
        description
          "ETH_1x50GE.";
      }
      enum "LAN_WAN_20x10GF_T_CARD" {
        value 166;
        description
          "LAN_WAN_20x10GF_T_CARD.";
      }
      enum "ETH_8x100GF_A_CARD" {
        value 167;
        description
          "ETH_8x100GF_A_CARD.";
      }
      enum "LAN_28x10GF_CARD(COMBO)" {
        value 168;
        description
          "LAN_28x10GF_CARD(COMBO).";
      }
      enum "WDM_8x100GC_CARD" {
        value 169;
        description
          "WDM_8x100GC_CARD.";
      }
      enum "ETH_2x100GF_LW_20x10GF" {
        value 170;
        description
          "ETH_2x100GF_LW_20x10GF.";
      }
      enum "LAN_WAN_24x10GF_CARD" {
        value 171;
        description
          "LAN_WAN_24x10GF_CARD.";
      }
      enum "ETH_4x100GF_CARD" {
        value 172;
        description
          "ETH_4x100GF_CARD.";
      }
      enum "OTN_4x100GF_CARD" {
        value 173;
        description
          "OTN_4x100GF_CARD.";
      }
      enum "LAN_WAN_48x10GF_CARD" {
        value 174;
        description
          "LAN_WAN_48x10GF_CARD.";
      }
      enum "ETH_24xGF_H_CARD" {
        value 175;
        description
          "ETH_24xGF_H_CARD.";
      }
      enum "ETH_1x100GC_F_CARD" {
        value 176;
        description
          "ETH_1x100GC_F_CARD.";
      }
      enum "ETH_1x100GB_A_CARD" {
        value 177;
        description
          "ETH_1x100GB_A_CARD.";
      }
      enum "ETH_2x100GB_B_CARD" {
        value 178;
        description
          "ETH_2x100GB_B_CARD.";
      }
      enum "ETH_2x100GB_A_CARD" {
        value 179;
        description
          "ETH_2x100GB_A_CARD.";
      }
      enum "ADM_1xLINE_8xMD_CARD" {
        value 180;
        description
          "ADM_1xLINE_8xMD_CARD.";
      }
      enum "LAN_WAN_6x10GF_I_CARD" {
        value 181;
        description
          "LAN_WAN_6x10GF_I_CARD.";
      }
      enum "LAN_WAN_12x10GF_T_CARD" {
        value 182;
        description
          "LAN_WAN_12x10GF_T_CARD.";
      }
      enum "POS_4x10GX_CARD" {
        value 183;
        description
          "POS_4x10GX_CARD.";
      }
      enum "FLEX_CR23MPAA_CARD" {
        value 184;
        description
          "FLEX_CR23MPAA_CARD.";
      }
      enum "FLEX_CR23SA8_CARD" {
        value 185;
        description
          "FLEX_CR23SA8_CARD.";
      }
      enum "FLEX_CR23MP8A_CARD" {
        value 186;
        description
          "FLEX_CR23MP8A_CARD.";
      }
      enum "NBP_NED1MPAA_CARD" {
        value 187;
        description
          "NBP_NED1MPAA_CARD.";
      }
      enum "NBP_NED1SA8_CARD" {
        value 188;
        description
          "NBP_NED1SA8_CARD.";
      }
      enum "NBP_NED1MP8A_CARD" {
        value 189;
        description
          "NBP_NED1MP8A_CARD.";
      }
      enum "ETH_20x100GF_CARD" {
        value 190;
        description
          "ETH_20x100GF_CARD.";
      }
      enum "ETH_4x400GC_CARD" {
        value 191;
        description
          "ETH_4x400GC_CARD.";
      }
      enum "OTN_8x100GB_CARD" {
        value 192;
        description
          "OTN_8x100GB_CARD.";
      }
      enum "ETH_8x100GB_CARD" {
        value 193;
        description
          "ETH_8x100GB_CARD.";
      }
      enum "ETH_2x400GB_CARD" {
        value 194;
        description
          "ETH_2x400GB_CARD.";
      }
      enum "ETH_8x100GF_CARD" {
        value 195;
        description
          "ETH_8x100GF_CARD.";
      }
      enum "ETH_2x400GC_CARD" {
        value 196;
        description
          "ETH_2x400GC_CARD.";
      }
      enum "ETH_2x50GB_CARD" {
        value 197;
        description
          "ETH_2x50GB_CARD.";
      }
      enum "OTN_4x10GX_CARD" {
        value 198;
        description
          "OTN_4x10GX_CARD.";
      }
      enum "NBP_NED1AT6_CARD" {
        value 199;
        description
          "NBP_NED1AT6_CARD.";
      }
      enum "FLEX_CR23AT6_CARD" {
        value 200;
        description
          "FLEX_CR23AT6_CARD.";
      }
      enum "ETH_2xGE_1xGE(c)_2xGE_6xFE" {
        value 201;
        description
          "ETH_2xGE_1xGE(c)_2xGE_6xFE.";
      }
      enum "ETH_8xFE" {
        value 202;
        description
          "ETH_8xFE.";
      }
      enum "ETH_100GB_CARD" {
        value 203;
        description
          "ETH_100GB_CARD.";
      }
      enum "ETH_2x100GB_CARD(COMBO)" {
        value 204;
        description
          "ETH_2x100GB_CARD(COMBO).";
      }
      enum "UNKNOWN_SUBCARD" {
        value 205;
        description
          "UNKNOWN_SUBCARD.";
      }
      enum "PDH_32xE1" {
        value 206;
        description
          "PDH_32xE1.";
      }
      enum "PDH_16xE1" {
        value 207;
        description
          "PDH_16xE1.";
      }
      enum "ETH_8xGE" {
        value 208;
        description
          "ETH_8xGE.";
      }
      enum "ETH_2x10GE" {
        value 209;
        description
          "ETH_2x10GE.";
      }
      enum "ETH_1x40GE" {
        value 210;
        description
          "ETH_1x40GE.";
      }
      enum "ETH_1x10GE" {
        value 211;
        description
          "ETH_1x10GE.";
      }
      enum "ETH_4xGE" {
        value 212;
        description
          "ETH_4xGE.";
      }
      enum "ETH_4xGE_4xGE" {
        value 213;
        description
          "ETH_4xGE_4xGE.";
      }
      enum "PDH_32xE1S_CARD" {
        value 214;
        description
          "PDH_32xE1S_CARD.";
      }
      enum "PDH_32xE1T_CARD" {
        value 215;
        description
          "PDH_32xE1T_CARD.";
      }
      enum "PDH_16xE1S_R_CARD" {
        value 216;
        description
          "PDH_16xE1S_R_CARD.";
      }
      enum "PDH_16xE1T_R_CARD" {
        value 217;
        description
          "PDH_16xE1T_R_CARD.";
      }
      enum "ETH_AND2EM8T_CARD" {
        value 218;
        description
          "ETH_AND2EM8T_CARD.";
      }
      enum "ETH_AND2EX2S_CARD" {
        value 219;
        description
          "ETH_AND2EX2S_CARD.";
      }
      enum "ETH_ANJ1EX4S_CARD" {
        value 220;
        description
          "ETH_ANJ1EX4S_CARD.";
      }
      enum "ETH_ANJ1EXL1_CARD" {
        value 221;
        description
          "ETH_ANJ1EXL1_CARD.";
      }
      enum "ETH_AND2EM8F_CARD" {
        value 222;
        description
          "ETH_AND2EM8F_CARD.";
      }
      enum "ETH_AND2EX1S_CARD" {
        value 223;
        description
          "ETH_AND2EX1S_CARD.";
      }
      enum "ETH_AND2EM4F_CARD" {
        value 224;
        description
          "ETH_AND2EM4F_CARD.";
      }
      enum "ETH_AND2EM4T_CARD" {
        value 225;
        description
          "ETH_AND2EM4T_CARD.";
      }
      enum "ETH_1x10GE_8xGE" {
        value 226;
        description
          "ETH_1x10GE_8xGE.";
      }
      enum "ETH_4x10GE_16xGE_8xGE" {
        value 227;
        description
          "ETH_4x10GE_16xGE_8xGE.";
      }
      enum "ETH_4x10GE_24xGE" {
        value 228;
        description
          "ETH_4x10GE_24xGE.";
      }
      enum "SDH_4xCPOS" {
        value 229;
        description
          "SDH_4xCPOS.";
      }
      enum "ETH_4x10GE" {
        value 230;
        description
          "ETH_4x10GE.";
      }
      enum "ETH_20xGE" {
        value 231;
        description
          "ETH_20xGE.";
      }
      enum "ETH_4x10GE_8xGE_8xGE" {
        value 232;
        description
          "ETH_4x10GE_8xGE_8xGE.";
      }
      enum "ETH_4x10GE_4xGE_4xGE" {
        value 233;
        description
          "ETH_4x10GE_4xGE_4xGE.";
      }
      enum "LAN_WAN_10x10GF_CARD" {
        value 234;
        description
          "LAN_WAN_10x10GF_CARD.";
      }
      enum "ETH_100GC_CARD" {
        value 235;
        description
          "ETH_100GC_CARD.";
      }
      enum "ETH_2x100GB_30x10GF_10xGF" {
        value 236;
        description
          "ETH_2x100GB_30x10GF_10xGF.";
      }
      enum "ETH_4xGED_CARD" {
        value 237;
        description
          "ETH_4xGED_CARD.";
      }
      enum "OTN_1x100GC_CARD" {
        value 238;
        description
          "OTN_1x100GC_CARD.";
      }
      enum "ETH_2x100GB_T_CARD" {
        value 239;
        description
          "ETH_2x100GB_T_CARD.";
      }
      enum "ETH_2xGE_2xGE(c)_2xGE" {
        value 240;
        description
          "ETH_2xGE_2xGE(c)_2xGE.";
      }
      enum "16E1_8GF(o)_8GF(e)_2XGE(o)" {
        value 241;
        description
          "16E1_8GF(o)_8GF(e)_2XGE(o).";
      }
      enum "16GF(o)_8GF(e)_2XGE(o)" {
        value 242;
        description
          "16GF(o)_8GF(e)_2XGE(o).";
      }
      enum "24GF(o)_4XGE(o)" {
        value 243;
        description
          "24GF(o)_4XGE(o).";
      }
      enum "16GF(o)_8GF(e)_4XGE(o)" {
        value 244;
        description
          "16GF(o)_8GF(e)_4XGE(o).";
      }
      enum "ETH_2x50GE" {
        value 245;
        description
          "ETH_2x50GE.";
      }
      enum "LW_6x10GF_ETH_4xGF_CARD" {
        value 246;
        description
          "LW_6x10GF_ETH_4xGF_CARD.";
      }
      enum "ETH_4xGF_CARD" {
        value 247;
        description
          "ETH_4xGF_CARD.";
      }
      enum "ETH_2x25GE" {
        value 248;
        description
          "ETH_2x25GE.";
      }
      enum "ETH_4x25GE" {
        value 249;
        description
          "ETH_4x25GE.";
      }
      enum "ETH_4x25GB_CARD" {
        value 250;
        description
          "ETH_4x25GB_CARD.";
      }
      enum "LAN_20x100GB_CARD(COMBO)" {
        value 251;
        description
          "LAN_20x100GB_CARD(COMBO).";
      }
      enum "ETH_4x100GB_10x10GF_10xGF" {
        value 252;
        description
          "ETH_4x100GB_10x10GF_10xGF.";
      }
      enum "ETH_6x10GE_20xGE_4xGE" {
        value 253;
        description
          "ETH_6x10GE_20xGE_4xGE.";
      }
      enum "ETH_1x25GE" {
        value 254;
        description
          "ETH_1x25GE.";
      }
      enum "ETH_4x25GF_CARD" {
        value 255;
        description
          "ETH_4x25GF_CARD.";
      }
      enum "ETH_8x25GF_CARD" {
        value 256;
        description
          "ETH_8x25GF_CARD.";
      }
      enum "ETH_8x25GB_CARD" {
        value 257;
        description
          "ETH_8x25GB_CARD.";
      }
      enum "ETH_4x50GB_T_CARD" {
        value 258;
        description
          "ETH_4x50GB_T_CARD.";
      }
      enum "ETH_8x50GB_CARD" {
        value 259;
        description
          "ETH_8x50GB_CARD.";
      }
      enum "ETH_16x25GF_CARD" {
        value 260;
        description
          "ETH_16x25GF_CARD.";
      }
      enum "ETH_10x10GB_CARD" {
        value 261;
        description
          "ETH_10x10GB_CARD.";
      }
      enum "ETH_20x100GB_CARD" {
        value 262;
        description
          "ETH_20x100GB_CARD.";
      }
      enum "ETH_36x10GF_CARD" {
        value 263;
        description
          "ETH_36x10GF_CARD.";
      }
      enum "ETH_10x100GB_CARD" {
        value 264;
        description
          "ETH_10x100GB_CARD.";
      }
      enum "ETH_4x400GB_4x100GB_CARD" {
        value 265;
        description
          "ETH_4x400GB_4x100GB_CARD.";
      }
      enum "ETH_5x10GE_3xGE_4xGE" {
        value 266;
        description
          "ETH_5x10GE_3xGE_4xGE.";
      }
      enum "FLEXE_16xMDE1_CARD" {
        value 267;
        description
          "FLEXE_16xMDE1_CARD.";
      }
      enum "ETH_8x100G_20x25G_28x10G" {
        value 268;
        description
          "ETH_8x100G_20x25G_28x10G.";
      }
      enum "ETH_10xGF_CARD" {
        value 269;
        description
          "ETH_10xGF_CARD.";
      }
      enum "ETH_16x10GE_12xGE_4xGE" {
        value 270;
        description
          "ETH_16x10GE_12xGE_4xGE.";
      }
      enum "FLEX_16xMDE1_CARD" {
        value 271;
        description
          "FLEX_16xMDE1_CARD.";
      }
      enum "ETH_60x25GF_CARD" {
        value 272;
        description
          "ETH_60x25GF_CARD.";
      }
      enum "ETH_40x100GB_CARD" {
        value 273;
        description
          "ETH_40x100GB_CARD.";
    }
      enum "ETH_72x25GF_CARD" {
        value 274;
    description
          "ETH_72x25GF_CARD.";
      }
      enum "ETH_8x400GB_8x100GB_CARD" {
        value 275;
        description
          "ETH_8x400GB_8x100GB_CARD.";
      }
     enum "LW_20x10GF_ETH_20xGF_CARD" {
        value 276;
        description
          "LW_20x10GF_ETH_20xGF_CARD.";
      }
      enum "LAN_WAN_20x10GF_CARD" {
        value 277;
        description
          "LAN_WAN_20x10GF_CARD.";
      }
     enum "ETH_20xGF_CARD" {
        value 278;
        description
          "ETH_20xGF_CARD.";
      }
      enum "FLEX_24XCE1_CARD" {
        value 279;
        description
          "FLEX_24XCE1_CARD.";
      }
    }
    description
      "Hardware-cardhard-type.";
  }
    typedef hardware-subcard-type {
    type enumeration {
      enum "unknown" {
        value 1;
        description
          "Unknown card.";
      }
      enum "CR5D00EJXF60" {
        value 2;
        description
          "CR5D00EJXF60.";
      }
      enum "CR2D00EEGF10" {
        value 3;
        description
          "CR2D00EEGF10.";
      }
      enum "CR5D00EEGF70" {
        value 4;
        description
          "CR5D00EEGF70.";
      }
      enum "CR57E8NCB0" {
        value 5;
        description
          "CR57E8NCB0.";
      }
      enum "ME0D00E8GE71" {
        value 6;
        description
          "ME0D00E8GE71.";
      }
      enum "ME0D00EAGF70" {
        value 7;
        description
          "ME0D00EAGF70.";
      }
      enum "ME0D00L4XF72" {
        value 8;
        description
          "ME0D00L4XF72.";
      }
      enum "ME0DL1XE8G71" {
        value 9;
        description
          "ME0DL1XE8G71.";
      }
      enum "ME0D00L2XF71" {
        value 10;
        description
          "ME0D00L2XF71.";
      }
      enum "ME0D00L4XF70" {
        value 11;
        description
          "ME0D00L4XF70.";
      }
      enum "ME0DL1XE8G70" {
        value 12;
        description
          "ME0DL1XE8G70.";
      }
      enum "ME0D00L2XF70" {
        value 13;
        description
          "ME0D00L2XF70.";
      }
      enum "ME0D00E8GF71" {
        value 14;
        description
          "ME0D00E8GF71.";
      }
      enum "ME0D00E8GE70" {
        value 15;
        description
          "ME0D00E8GE70.";
      }
      enum "ME0D00C4CF71" {
        value 16;
        description
          "ME0D00C4CF71.";
      }
      enum "ME0D000IE170" {
        value 17;
        description
          "ME0D000IE170.";
      }
      enum "ME0D000IE171" {
        value 18;
        description
          "ME0D000IE171.";
      }
      enum "ME0D000DE170" {
        value 19;
        description
          "ME0D000DE170.";
      }
      enum "ME0D000DE171" {
        value 20;
        description
          "ME0D000DE171.";
      }
      enum "ME0D00P4CF70" {
        value 21;
        description
          "ME0D00P4CF70.";
      }
      enum "ME0DP2C1HF70" {
        value 22;
        description
          "ME0DP2C1HF70.";
      }
      enum "ME0D00AUXQ10" {
        value 23;
        description
          "ME0D00AUXQ10.";
      }
      enum "ME0D08CWDM70" {
        value 24;
        description
          "ME0D08CWDM70.";
      }
      enum "ME0D00C4T370" {
        value 25;
        description
          "ME0D00C4T370.";
      }
      enum "ME0D0EAGFH70" {
        value 26;
        description
          "ME0D0EAGFH70.";
      }
      enum "ME0D0L2XFH71" {
        value 27;
        description
          "ME0D0L2XFH71.";
      }
      enum "ME2D00E8GE12" {
        value 28;
        description
          "ME2D00E8GE12.";
      }
      enum "ME2D00EAGF10" {
        value 29;
        description
          "ME2D00EAGF10.";
      }
      enum "ME2D00L4XF11" {
        value 30;
        description
          "ME2D00L4XF11.";
      }
      enum "ME2DL1XE8G11" {
        value 31;
        description
          "ME2DL1XE8G11.";
      }
      enum "ME2D00L2XF12" {
        value 32;
        description
          "ME2D00L2XF12.";
      }
      enum "CR5D00P2XX72" {
        value 33;
        description
          "CR5D00P2XX72.";
      }
      enum "CR57L4XEBG0" {
        value 34;
        description
          "CR57L4XEBG0.";
      }
      enum "CR57TBXF00" {
        value 35;
        description
          "CR57TBXF00.";
      }
      enum "CR57T6XF00" {
        value 36;
        description
          "CR57T6XF00.";
      }
      enum "CR5D00T1MC60" {
        value 37;
        description
          "CR5D00T1MC60.";
      }
      enum "CR5D00TBXF70" {
        value 38;
        description
          "CR5D00TBXF70.";
      }
      enum "CR5D00T6XF70" {
        value 39;
        description
          "CR5D00T6XF70.";
      }
      enum "CR53CFE10" {
        value 40;
        description
          "CR53CFE10.";
      }
      enum "CR5D00C2CF70" {
        value 41;
        description
          "CR5D00C2CF70.";
      }
      enum "CR5D00C4CF70" {
        value 42;
        description
          "CR5D00C4CF70.";
      }
      enum "CR5D00C8CF71" {
        value 43;
        description
          "CR5D00C8CF71.";
      }
      enum "CX6D00C8CF10" {
        value 44;
        description
          "CX6D00C8CF10.";
      }
      enum "CX6D0L2XFA10" {
        value 45;
        description
          "CX6D0L2XFA10.";
      }
      enum "CR57L3XFB0" {
        value 46;
        description
          "CR57L3XFB0.";
      }
      enum "CR57L2XFB2" {
        value 47;
        description
          "CR57L2XFB2.";
      }
      enum "CR57L4XFB2" {
        value 48;
        description
          "CR57L4XFB2.";
      }
      enum "CR57L5XFB2" {
        value 49;
        description
          "CR57L5XFB2.";
      }
      enum "CR57EMGFC0" {
        value 50;
        description
          "CR57EMGFC0.";
      }
      enum "CR57EFGFC0" {
        value 51;
        description
          "CR57EFGFC0.";
      }
      enum "CR57L1XEDG0" {
        value 52;
        description
          "CR57L1XEDG0.";
      }
      enum "ME0D0LBXXB7H" {
        value 53;
        description
          "ME0D0LBXXB7H.";
      }
      enum "ME0D2L1NXB7H" {
        value 54;
        description
          "ME0D2L1NXB7H.";
      }
      enum "ME0D0L1NXB7H" {
        value 55;
        description
          "ME0D0L1NXB7H.";
      }
      enum "CX6D0E2NCA10" {
        value 56;
        description
          "CX6D0E2NCA10.";
      }
      enum "CX6D0LFXFA11" {
        value 57;
        description
          "CX6D0LFXFA11.";
      }
      enum "ME0D0LAXFE7H" {
        value 58;
        description
          "ME0D0LAXFE7H.";
      }
      enum "ME0D0LAXFB7H" {
        value 59;
        description
          "ME0D0LAXFB7H.";
      }
      enum "ME0D0LAXFH7H" {
        value 60;
        description
          "ME0D0LAXFH7H.";
      }
      enum "ME0DE4NE8V70" {
        value 61;
        description
          "ME0DE4NE8V70.";
      }
      enum "CR5DE4NE8V70" {
        value 62;
        description
          "CR5DE4NE8V70.";
      }
      enum "CX6DE4NE8V10" {
        value 63;
        description
          "CX6DE4NE8V10.";
      }
      enum "CX6D0EDYFA10" {
        value 64;
        description
          "CX6D0EDYFA10.";
      }
      enum "CR57LAXFB1" {
        value 65;
        description
          "CR57LAXFB1.";
      }
      enum "CR5D00EDYB70" {
        value 66;
        description
          "CR5D00EDYB70.";
      }
      enum "CX62E8YFA0" {
        value 67;
        description
          "CX62E8YFA0.";
      }
      enum "CX62E2NBD0" {
        value 68;
        description
          "CX62E2NBD0.";
      }
      enum "CR57LFXFF0" {
        value 69;
        description
          "CR57LFXFF0.";
      }
      enum "CR57LFXFF1" {
        value 70;
        description
          "CR57LFXFF1.";
      }
      enum "CR57EKGFB0" {
        value 71;
        description
          "CR57EKGFB0.";
      }
      enum "CR57EKGFB1" {
        value 72;
        description
          "CR57EKGFB1.";
      }
      enum "CR57E4VBA0" {
        value 73;
        description
          "CR57E4VBA0.";
      }
      enum "CR57E4VBA1" {
        value 74;
        description
          "CR57E4VBA1.";
      }
      enum "CR57E4VBB0" {
        value 75;
        description
          "CR57E4VBB0.";
      }
      enum "CR57E8YFA0" {
        value 76;
        description
          "CR57E8YFA0.";
      }
      enum "CR57E2NLEXB1" {
        value 77;
        description
          "CR57E2NLEXB1.";
      }
      enum "NEDD00EV1Q00" {
        value 78;
        description
          "NEDD00EV1Q00.";
      }
      enum "GPR8CQ20YS" {
        value 79;
        description
          "GPR8CQ20YS.";
      }
      enum "CX62E4NBC0" {
        value 80;
        description
          "CX62E4NBC0.";
      }
      enum "CR57E4NBC0" {
        value 81;
        description
          "CR57E4NBC0.";
      }
      enum "CR57E4NBC1" {
        value 82;
        description
          "CR57E4NBC1.";
      }
      enum "ANKD001EV203" {
        value 83;
        description
          "ANKD001EV203.";
      }
      enum "ANKD001EV204" {
        value 84;
        description
          "ANKD001EV204.";
      }
      enum "ANKD00EX4S01" {
        value 85;
        description
          "ANKD00EX4S01.";
      }
      enum "ANKD00EX2S01" {
        value 86;
        description
          "ANKD00EX2S01.";
      }
      enum "ANDD0EM10F00" {
        value 87;
        description
          "ANDD0EM10F00.";
      }
      enum "CR57LKXFB0" {
        value 88;
        description
          "CR57LKXFB0.";
      }
      enum "CR57LKXFB1" {
        value 89;
        description
          "CR57LKXFB1.";
      }
      enum "CR56LFXFB3" {
        value 90;
        description
          "CR56LFXFB3.";
      }
      enum "CR58LPXFA0" {
        value 91;
        description
          "CR58LPXFA0.";
      }
      enum "CR57L2XEIG0" {
        value 92;
        description
          "CR57L2XEIG0.";
      }
      enum "CR57L5XFC0" {
        value 93;
        description
          "CR57L5XFC0.";
      }
      enum "ME0D0L5XXE7H" {
        value 94;
        description
          "ME0D0L5XXE7H.";
      }
      enum "ME0D0L6XXB7H" {
        value 95;
        description
          "ME0D0L6XXB7H.";
      }
      enum "ME0D0L2XXE7H" {
        value 96;
        description
          "ME0D0L2XXE7H.";
      }
      enum "ME0D0L5XXE7F" {
        value 97;
        description
          "ME0D0L5XXE7F.";
      }
      enum "ME0D0EFGFE7H" {
        value 98;
        description
          "ME0D0EFGFE7H.";
      }
      enum "ME0D0L2XXB7H" {
        value 99;
        description
          "ME0D0L2XXB7H.";
      }
      enum "ME0D0L5XXB7F" {
        value 100;
        description
          "ME0D0L5XXB7F.";
      }
      enum "ME0D0L5XXB7H" {
        value 101;
        description
          "ME0D0L5XXB7H.";
      }
      enum "ME0D0EFGFB7H" {
        value 102;
        description
          "ME0D0EFGFB7H.";
      }
      enum "CR57D2NT00" {
        value 103;
        description
          "CR57D2NT00.";
      }
      enum "CR53P8CF0" {
        value 104;
        description
          "CR53P8CF0.";
      }
      enum "CR53P4CF0" {
        value 105;
        description
          "CR53P4CF0.";
      }
      enum "CR5D00P2CF70" {
        value 106;
        description
          "CR5D00P2CF70.";
      }
      enum "CR2D00T4XF70" {
        value 107;
        description
          "CR2D00T4XF70.";
      }
      enum "CR2D00E1MF70" {
        value 108;
        description
          "CR2D00E1MF70.";
      }
      enum "CR5D00E1MF70" {
        value 109;
        description
          "CR5D00E1MF70.";
      }
      enum "CR5D00T4XF70" {
        value 110;
        description
          "CR5D00T4XF70.";
      }
      enum "CR5D0L5XFA7L" {
        value 111;
        description
          "CR5D0L5XFA7L.";
      }
      enum "CR5DL2XEIG7L" {
        value 112;
        description
          "CR5DL2XEIG7L.";
      }
      enum "CR5D0EMGFA7L" {
        value 113;
        description
          "CR5D0EMGFA7L.";
      }
      enum "CR5D0L5XFA72" {
        value 114;
        description
          "CR5D0L5XFA72.";
      }
      enum "CR5D0LBXFE7E" {
        value 115;
        description
          "CR5D0LBXFE7E.";
      }
      enum "CR5D00L1NC7E" {
        value 116;
        description
          "CR5D00L1NC7E.";
      }
      enum "ME0D00L1NC7E" {
        value 117;
        description
          "ME0D00L1NC7E.";
      }
      enum "ME0D0LBXFE7E" {
        value 118;
        description
          "ME0D0LBXFE7E.";
      }
      enum "CR5D0LAXFE70" {
        value 119;
        description
          "CR5D0LAXFE70.";
      }
      enum "CR5D00LAXF70" {
        value 120;
        description
          "CR5D00LAXF70.";
      }
      enum "CR5D0L5XFA70" {
        value 121;
        description
          "CR5D0L5XFA70.";
      }
      enum "CR5M0E8GFA30" {
        value 122;
        description
          "CR5M0E8GFA30.";
      }
      enum "CR5D0L2XFA70" {
        value 123;
        description
          "CR5D0L2XFA70.";
      }
      enum "CR5D0EEGEA70" {
        value 124;
        description
          "CR5D0EEGEA70.";
      }
      enum "CR5D00L2XEFGFA71" {
        value 125;
        description
          "CR5D00L2XEFGFA71.";
      }
      enum "CR5D00L4XEKGFB71" {
        value 126;
        description
          "CR5D00L4XEKGFB71.";
      }
      enum "CR5D00AUXQ10" {
        value 127;
        description
          "CR5D00AUXQ10.";
      }
      enum "CR2D0L2XFH10" {
        value 128;
        description
          "CR2D0L2XFH10.";
      }
      enum "CR5D0L2XFH71" {
        value 129;
        description
          "CR5D0L2XFH71.";
      }
      enum "CR2D00L2XF12" {
        value 130;
        description
          "CR2D00L2XF12.";
      }
      enum "CX6D00L2XF11" {
        value 131;
        description
          "CX6D00L2XF11.";
      }
      enum "CR5D08CWDM70" {
        value 132;
        description
          "CR5D08CWDM70.";
      }
      enum "CR5D00L2XF71" {
        value 133;
        description
          "CR5D00L2XF71.";
      }
      enum "CR2D00E8GE12" {
        value 134;
        description
          "CR2D00E8GE12.";
      }
      enum "CX6D00E8GE11" {
        value 135;
        description
          "CX6D00E8GE11.";
      }
      enum "CR5D00E8GE71" {
        value 136;
        description
          "CR5D00E8GE71.";
      }
      enum "CR2DL1XE8G11" {
        value 137;
        description
          "CR2DL1XE8G11.";
      }
      enum "CX6DL1XE8G11" {
        value 138;
        description
          "CX6DL1XE8G11.";
      }
      enum "CR5DL1XE8G71" {
        value 139;
        description
          "CR5DL1XE8G71.";
      }
      enum "CR2D00L4XF11" {
        value 140;
        description
          "CR2D00L4XF11.";
      }
      enum "CX6D00L4XF11" {
        value 141;
        description
          "CX6D00L4XF11.";
      }
      enum "CR5D00L4XF72" {
        value 142;
        description
          "CR5D00L4XF72.";
      }
      enum "CR2D00EAGF10" {
        value 143;
        description
          "CR2D00EAGF10.";
      }
      enum "CX6D00EAGF10" {
        value 144;
        description
          "CX6D00EAGF10.";
      }
      enum "CR5D00EAGF70" {
        value 145;
        description
          "CR5D00EAGF70.";
      }
      enum "CR2D0EAGFH10" {
        value 146;
        description
          "CR2D0EAGFH10.";
      }
      enum "CR5D0EAGFH70" {
        value 147;
        description
          "CR5D0EAGFH70.";
      }
      enum "CR52P2XX" {
        value 148;
        description
          "CR52P2XX.";
      }
      enum "CR57E8NC" {
        value 149;
        description
          "CR57E8NC.";
      }
      enum "CR52P4XX" {
        value 150;
        description
          "CR52P4XX.";
      }
      enum "CR52P8UF" {
        value 151;
        description
          "CR52P8UF.";
      }
      enum "CR52EEGF" {
        value 152;
        description
          "CR52EEGF.";
      }
      enum "CR52E1XX" {
        value 153;
        description
          "CR52E1XX.";
      }
      enum "CR52E4XX" {
        value 154;
        description
          "CR52E4XX.";
      }
      enum "CR52W4XX" {
        value 155;
        description
          "CR52W4XX.";
      }
      enum "CR52EAGF" {
        value 156;
        description
          "CR52EAGF.";
      }
      enum "CR52P4UF" {
        value 157;
        description
          "CR52P4UF.";
      }
      enum "CR52E2XX" {
        value 158;
        description
          "CR52E2XX.";
      }
      enum "CR52W2XX" {
        value 159;
        description
          "CR52W2XX.";
      }
      enum "CR52P1XX" {
        value 160;
        description
          "CR52P1XX.";
      }
      enum "CR52W1XX" {
        value 161;
        description
          "CR52W1XX.";
      }
      enum "CR56L5XX" {
        value 162;
        description
          "CR56L5XX.";
      }
      enum "CR56E1NC" {
        value 163;
        description
          "CR56E1NC.";
      }
      enum "CR56P2XX" {
        value 164;
        description
          "CR56P2XX.";
      }
      enum "CR56L2XX" {
        value 165;
        description
          "CR56L2XX.";
      }
      enum "CR56E2XX" {
        value 166;
        description
          "CR56E2XX.";
      }
      enum "CR56D2XX" {
        value 167;
        description
          "CR56D2XX.";
      }
      enum "CR56E5XX" {
        value 168;
        description
          "CR56E5XX.";
      }
      enum "CR56P1MZ" {
        value 169;
        description
          "CR56P1MZ.";
      }
      enum "CR56EFGF" {
        value 170;
        description
          "CR56EFGF.";
      }
      enum "CR52P8CF" {
        value 171;
        description
          "CR52P8CF.";
      }
      enum "CR2D00C1CF11" {
        value 172;
        description
          "CR2D00C1CF11.";
      }
      enum "CR52P2UF" {
        value 173;
        description
          "CR52P2UF.";
      }
      enum "CR52P1UF" {
        value 174;
        description
          "CR52P1UF.";
      }
      enum "CR55OFC100B" {
        value 175;
        description
          "CR55OFC100B.";
      }
      enum "CR55OFC400D" {
        value 176;
        description
          "CR55OFC400D.";
      }
      enum "CR5D0OFCK051" {
        value 177;
        description
          "CR5D0OFCK051.";
      }
      enum "CR55OFC400A" {
        value 178;
        description
          "CR55OFC400A.";
      }
      enum "CR5M0OFCK050" {
        value 179;
        description
          "CR5M0OFCK050.";
      }
      enum "CR55OFC1TA" {
        value 180;
        description
          "CR55OFC1TA.";
      }
      enum "CR5D0OFCT050" {
        value 181;
        description
          "CR5D0OFCT050.";
      }
      enum "CR55OFC400B" {
        value 182;
        description
          "CR55OFC400B.";
      }
      enum "CR55OFC1TB" {
        value 183;
        description
          "CR55OFC1TB.";
      }
      enum "CR55OFC2TA" {
        value 184;
        description
          "CR55OFC2TA.";
      }
      enum "CR55OFC2TB" {
        value 185;
        description
          "CR55OFC2TB.";
      }
      enum "CR50OFC1TC" {
        value 186;
        description
          "CR50OFC1TC.";
      }
      enum "CR50OFC1TD" {
        value 187;
        description
          "CR50OFC1TD.";
      }
      enum "CR52OFCB" {
        value 188;
        description
          "CR52OFCB.";
      }
      enum "CR55OFC100A" {
        value 189;
        description
          "CR55OFC100A.";
      }
      enum "CR55OFC40" {
        value 190;
        description
          "CR55OFC40.";
      }
      enum "CR55OFCA" {
        value 191;
        description
          "CR55OFCA.";
      }
      enum "CR55C-OFCA" {
        value 192;
        description
          "CR55C-OFCA.";
      }
      enum "CR52OFCV" {
        value 193;
        description
          "CR52OFCV.";
      }
      enum "CFCARD" {
        value 194;
        description
          "CF card.";
      }
      enum "CR53P1MZ" {
        value 195;
        description
          "CR53P1MZ.";
      }
      enum "CR52P4HF" {
        value 196;
        description
          "CR52P4HF.";
      }
      enum "CR52EMGE" {
        value 197;
        description
          "CR52EMGE.";
      }
      enum "CR52EFGE" {
        value 198;
        description
          "CR52EFGE.";
      }
      enum "CR52E5GF" {
        value 199;
        description
          "CR52E5GF.";
      }
      enum "CR52P4CF" {
        value 200;
        description
          "CR52P4CF.";
      }
      enum "CR52D1MV" {
        value 201;
        description
          "CR52D1MV.";
      }
      enum "CR52EKGFY" {
        value 202;
        description
          "CR52EKGFY.";
      }
      enum "CR57EFGF" {
        value 203;
        description
          "CR57EFGF.";
      }
      enum "CR56E1NCC" {
        value 204;
        description
          "CR56E1NCC.";
      }
      enum "CR52P1XZ" {
        value 205;
        description
          "CR52P1XZ.";
      }
      enum "CR52E1XZ" {
        value 206;
        description
          "CR52E1XZ.";
      }
      enum "CR52W1XZ" {
        value 207;
        description
          "CR52W1XZ.";
      }
      enum "SPU" {
        value 208;
        description
          "SPU.";
      }
      enum "TSUA" {
        value 209;
        description
          "TSUA.";
      }
      enum "CR56E1MC" {
        value 210;
        description
          "CR56E1MC.";
      }
      enum "CR56LAXFA" {
        value 211;
        description
          "CR56LAXFA.";
      }
      enum "CR56E2ND" {
        value 212;
        description
          "CR56E2ND.";
      }
      enum "CR56E6MB" {
        value 213;
        description
          "CR56E6MB.";
      }
      enum "CR56LEXF" {
        value 214;
        description
          "CR56LEXF.";
      }
      enum "CR56E1NCB" {
        value 215;
        description
          "CR56E1NCB.";
      }
      enum "CR56L5XFB" {
        value 216;
        description
          "CR56L5XFB.";
      }
      enum "CR56E5XFB" {
        value 217;
        description
          "CR56E5XFB.";
      }
      enum "CR56P8UF" {
        value 218;
        description
          "CR56P8UF.";
      }
      enum "CR56LFXF" {
        value 219;
        description
          "CR56LFXF.";
      }
      enum "CR56LFXF0" {
        value 220;
        description
          "CR56LFXF0.";
      }
      enum "CR56E2NCC" {
        value 221;
        description
          "CR56E2NCC.";
      }
      enum "CR56E5MB" {
        value 222;
        description
          "CR56E5MB.";
      }
      enum "CR5D00L5XX60" {
        value 223;
        description
          "CR5D00L5XX60.";
      }
      enum "CR5D00E5XX60" {
        value 224;
        description
          "CR5D00E5XX60.";
      }
      enum "CR5D00L2XX60" {
        value 225;
        description
          "CR5D00L2XX60.";
      }
      enum "CR5D00E2XX60" {
        value 226;
        description
          "CR5D00E2XX60.";
      }
      enum "CR5D00EFGF60" {
        value 227;
        description
          "CR5D00EFGF60.";
      }
      enum "CR5D00P1MZ60" {
        value 228;
        description
          "CR5D00P1MZ60.";
      }
      enum "CR5D00P2XX60" {
        value 229;
        description
          "CR5D00P2XX60.";
      }
      enum "CR5M00E1MC60" {
        value 230;
        description
          "CR5M00E1MC60.";
      }
      enum "CR5D00E1NC60" {
        value 231;
        description
          "CR5D00E1NC60.";
      }
      enum "CR5D00LAXX60" {
        value 232;
        description
          "CR5D00LAXX60.";
      }
      enum "CR5D00E2NC61" {
        value 233;
        description
          "CR5D00E2NC61.";
      }
      enum "CR5D00E6MF61" {
        value 234;
        description
          "CR5D00E6MF61.";
      }
      enum "CR5D00LEXF61" {
        value 235;
        description
          "CR5D00LEXF61.";
      }
      enum "CR5D00E1NC61" {
        value 236;
        description
          "CR5D00E1NC61.";
      }
      enum "CR5D00LMXF61" {
        value 237;
        description
          "CR5D00LMXF61.";
      }
      enum "CR5D00LAXF60" {
        value 238;
        description
          "CR5D00LAXF60.";
      }
      enum "CR5D00L5XF60" {
        value 239;
        description
          "CR5D00L5XF60.";
      }
      enum "CR5D00E5XF60" {
        value 240;
        description
          "CR5D00E5XF60.";
      }
      enum "CR5D00P8UF60" {
        value 241;
        description
          "CR5D00P8UF60.";
      }
      enum "CR5D00E2NC62" {
        value 242;
        description
          "CR5D00E2NC62.";
      }
      enum "CR5D00E5MF61" {
        value 243;
        description
          "CR5D00E5MF61.";
      }
      enum "CR5D0OFCA060" {
        value 244;
        description
          "CR5D0OFCA060.";
      }
      enum "CX6D00E8GE10" {
        value 245;
        description
          "CX6D00E8GE10.";
      }
      enum "CR5D00E8GE70" {
        value 246;
        description
          "CR5D00E8GE70.";
      }
      enum "CR2D00E8GE11" {
        value 247;
        description
          "CR2D00E8GE11.";
      }
      enum "CX6D00L2XF10" {
        value 248;
        description
          "CX6D00L2XF10.";
      }
      enum "CR5D00L2XF70" {
        value 249;
        description
          "CR5D00L2XF70.";
      }
      enum "CR2D00L2XF11" {
        value 250;
        description
          "CR2D00L2XF11.";
      }
      enum "CX6D00E8GF10" {
        value 251;
        description
          "CX6D00E8GF10.";
      }
      enum "CR5D00E8GF71" {
        value 252;
        description
          "CR5D00E8GF71.";
      }
      enum "CR2D00E8GF11" {
        value 253;
        description
          "CR2D00E8GF11.";
      }
      enum "CX6D000IE170" {
        value 254;
        description
          "CX6D000IE170.";
      }
      enum "CX6D000IE171" {
        value 255;
        description
          "CX6D000IE171.";
      }
      enum "CR5D00P4CF70" {
        value 256;
        description
          "CR5D00P4CF70.";
      }
      enum "CR2D00P4CF11" {
        value 257;
        description
          "CR2D00P4CF11.";
      }
      enum "CX6D00L4XF10" {
        value 258;
        description
          "CX6D00L4XF10.";
      }
      enum "CR5D00L4XF70" {
        value 259;
        description
          "CR5D00L4XF70.";
      }
      enum "CR2D00L4XF10" {
        value 260;
        description
          "CR2D00L4XF10.";
      }
      enum "CX6DL1XE8G10" {
        value 261;
        description
          "CX6DL1XE8G10.";
      }
      enum "CR5DL1XE8G70" {
        value 262;
        description
          "CR5DL1XE8G70.";
      }
      enum "CR2DL1XE8G10" {
        value 263;
        description
          "CR2DL1XE8G10.";
      }
      enum "CR5D00C4CF71" {
        value 264;
        description
          "CR5D00C4CF71.";
      }
      enum "CX6D00C4CF11" {
        value 265;
        description
          "CX6D00C4CF11.";
      }
      enum "CR2D00C4CF11" {
        value 266;
        description
          "CR2D00C4CF11.";
      }
      enum "CR5D000IE170" {
        value 267;
        description
          "CR5D000IE170.";
      }
      enum "CX6D000IE110" {
        value 268;
        description
          "CX6D000IE110.";
      }
      enum "CR2D000IE110" {
        value 269;
        description
          "CR2D000IE110.";
      }
      enum "CR5D000IE171" {
        value 270;
        description
          "CR5D000IE171.";
      }
      enum "CX6D000IE111" {
        value 271;
        description
          "CX6D000IE111.";
      }
      enum "CR2D000IE111" {
        value 272;
        description
          "CR2D000IE111.";
      }
      enum "CR5D000DE170" {
        value 273;
        description
          "CR5D000DE170.";
      }
      enum "CX6D000DE110" {
        value 274;
        description
          "CX6D000DE110.";
      }
      enum "CR2D000DE110" {
        value 275;
        description
          "CR2D000DE110.";
      }
      enum "CR5D000DE171" {
        value 276;
        description
          "CR5D000DE171.";
      }
      enum "CX6D000DE111" {
        value 277;
        description
          "CX6D000DE111.";
      }
      enum "CR2D000DE111" {
        value 278;
        description
          "CR2D000DE111.";
      }
      enum "CR5D00C4T370" {
        value 279;
        description
          "CR5D00C4T370.";
      }
      enum "CR57EFGFB" {
        value 280;
        description
          "CR57EFGFB.";
      }
      enum "CR57EFGFB2" {
        value 281;
        description
          "CR57EFGFB2.";
      }
      enum "CR57LBXF" {
        value 282;
        description
          "CR57LBXF.";
      }
      enum "CR57LBXF2" {
        value 283;
        description
          "CR57LBXF2.";
      }
      enum "CR57E1NCB2" {
        value 284;
        description
          "CR57E1NCB2.";
      }
      enum "CR9D00EANB83" {
        value 285;
        description
          "CR9D00EANB83.";
      }
      enum "CR9D00D8NC81" {
        value 286;
        description
          "CR9D00D8NC81.";
      }
      enum "CR57EBGFD0" {
        value 287;
        description
          "CR57EBGFD0.";
      }
      enum "CR57L6XF" {
        value 288;
        description
          "CR57L6XF.";
      }
      enum "CR57L6XF0" {
        value 289;
        description
          "CR57L6XF0.";
      }
      enum "CR57L6XFB" {
        value 290;
        description
          "CR57L6XFB.";
      }
      enum "CR57P8UF" {
        value 291;
        description
          "CR57P8UF.";
      }
      enum "CR5D0P8UF70" {
        value 292;
        description
          "CR5D0P8UF70.";
      }
      enum "CR57E1MCB" {
        value 293;
        description
          "CR57E1MCB.";
      }
      enum "CR57E1MCB2" {
        value 294;
        description
          "CR57E1MCB2.";
      }
      enum "CX68MD8A" {
        value 295;
        description
          "CX68MD8A.";
      }
      enum "CR56E8NC" {
        value 296;
        description
          "CR56E8NC.";
      }
      enum "CR56EFMB" {
        value 297;
        description
          "CR56EFMB.";
      }
      enum "CR50OFC400C" {
        value 298;
        description
          "CR50OFC400C.";
      }
      enum "CR5D00LFXF74" {
        value 299;
        description
          "CR5D00LFXF74.";
      }
      enum "CR5D00E2NC72" {
        value 300;
        description
          "CR5D00E2NC72.";
      }
      enum "CR57LFXFE1" {
        value 301;
        description
          "CR57LFXFE1.";
      }
      enum "CR57E2NCE1" {
        value 302;
        description
          "CR57E2NCE1.";
      }
      enum "CR57LFXFE" {
        value 303;
        description
          "CR57LFXFE.";
      }
      enum "CR57E2NCE" {
        value 304;
        description
          "CR57E2NCE.";
      }
      enum "CR5D00LBXF72" {
        value 305;
        description
          "CR5D00LBXF72.";
      }
      enum "CR5D0L6XFA70" {
        value 306;
        description
          "CR5D0L6XFA70.";
      }
      enum "CR5D00E1NC75" {
        value 307;
        description
          "CR5D00E1NC75.";
      }
      enum "CR5D0EFGFA71" {
        value 308;
        description
          "CR5D0EFGFA71.";
      }
      enum "CR5D00E1MC70" {
        value 309;
        description
          "CR5D00E1MC70.";
      }
      enum "CR5D00P8UF70" {
        value 310;
        description
          "CR5D00P8UF70.";
      }
      enum "CR5D00E1NC74" {
        value 311;
        description
          "CR5D00E1NC74.";
      }
      enum "CR5D00LBXF71" {
        value 312;
        description
          "CR5D00LBXF71.";
      }
      enum "CR57L2XFB" {
        value 313;
        description
          "CR57L2XFB.";
      }
      enum "CR5D0L2XFA71" {
        value 314;
        description
          "CR5D0L2XFA71.";
      }
      enum "CR5D0EFGFA70" {
        value 315;
        description
          "CR5D0EFGFA70.";
      }
      enum "CR57L2XFC2" {
        value 316;
        description
          "CR57L2XFC2.";
      }
      enum "CR2DP4C2HF11" {
        value 317;
        description
          "CR2DP4C2HF11.";
      }
      enum "CR5DP4C2HF70" {
        value 318;
        description
          "CR5DP4C2HF70.";
      }
      enum "CR2DP2C1HF11" {
        value 319;
        description
          "CR2DP2C1HF11.";
      }
      enum "CR5DP2C1HF70" {
        value 320;
        description
          "CR5DP2C1HF70.";
      }
      enum "CR5D00N2NC61" {
        value 321;
        description
          "CR5D00N2NC61.";
      }
      enum "CR5D00E1NC62" {
        value 322;
        description
          "CR5D00E1NC62.";
      }
      enum "CR5D00L2NC63" {
        value 323;
        description
          "CR5D00L2NC63.";
      }
      enum "CR5D00LEXF63" {
        value 324;
        description
          "CR5D00LEXF63.";
      }
      enum "CR5D00SP8010" {
        value 325;
        description
          "CR5D00SP8010.";
      }
      enum "CR5D00SPD010" {
        value 326;
        description
          "CR5D00SPD010.";
      }
      enum "ME0D00SP8070" {
        value 327;
        description
          "ME0D00SP8070.";
      }
      enum "ME0D00SPD070" {
        value 328;
        description
          "ME0D00SPD070.";
      }
      enum "ME0D00SP8071" {
        value 329;
        description
          "ME0D00SP8071.";
      }
      enum "ME0D00SPD071" {
        value 330;
        description
          "ME0D00SPD071.";
      }
      enum "CX6D0E8GFA10" {
        value 331;
        description
          "CX6D0E8GFA10.";
      }
      enum "CX6D00CFE110" {
        value 332;
        description
          "CX6D00CFE110.";
      }
      enum "CX6D00C2CF10" {
        value 333;
        description
          "CX6D00C2CF10.";
      }
      enum "CR53C2CF0" {
        value 334;
        description
          "CR53C2CF0.";
      }
      enum "CX6D0L5XFA10" {
        value 335;
        description
          "CX6D0L5XFA10.";
      }
      enum "CX6D0L2XFA11" {
        value 336;
        description
          "CX6D0L2XFA11.";
      }
      enum "CX6D0EFGFA10" {
        value 337;
        description
          "CX6D0EFGFA10.";
      }
      enum "CX6D0EEGEA10" {
        value 338;
        description
          "CX6D0EEGEA10.";
      }
      enum "CX6DL1XESG1A" {
        value 339;
        description
          "CX6DL1XESG1A.";
      }
      enum "CX6DL2XEAG1A" {
        value 340;
        description
          "CX6DL2XEAG1A.";
      }
      enum "CX6D0L5XFA12" {
        value 341;
        description
          "CX6D0L5XFA12.";
      }
      enum "CX6D0EFGFA11" {
        value 342;
        description
          "CX6D0EFGFA11.";
      }
      enum "CX6D0E1NCA10" {
        value 343;
        description
          "CX6D0E1NCA10.";
      }
      enum "CX6D0E1MCA10" {
        value 344;
        description
          "CX6D0E1MCA10.";
      }
      enum "CX6D0L5XFH10" {
        value 345;
        description
          "CX6D0L5XFH10.";
      }
      enum "CX6D0L6XFA10" {
        value 346;
        description
          "CX6D0L6XFA10.";
      }
      enum "CX6D0LBXFA10" {
        value 347;
        description
          "CX6D0LBXFA10.";
      }
      enum "CX6D0LAXFA12" {
        value 348;
        description
          "CX6D0LAXFA12.";
      }
      enum "CX6D0E3MFA10" {
        value 349;
        description
          "CX6D0E3MFA10.";
      }
      enum "CX6D0LAXFH10" {
        value 350;
        description
          "CX6D0LAXFH10.";
      }
      enum "CX6D0LBXFA12" {
        value 351;
        description
          "CX6D0LBXFA12.";
      }
      enum "CR5D0EFGFE70" {
        value 352;
        description
          "CR5D0EFGFE70.";
      }
      enum "CR5D00E1NC7D" {
        value 353;
        description
          "CR5D00E1NC7D.";
      }
      enum "CR5D0L5XFE70" {
        value 354;
        description
          "CR5D0L5XFE70.";
      }
      enum "CR56LEXF3" {
        value 355;
        description
          "CR56LEXF3.";
      }
      enum "CR5D0L2XFE70" {
        value 356;
        description
          "CR5D0L2XFE70.";
      }
      enum "CR5D0L2XFH70" {
        value 357;
        description
          "CR5D0L2XFH70.";
      }
      enum "CR5D0L5XFE71" {
        value 358;
        description
          "CR5D0L5XFE71.";
      }
      enum "CR5D0L5XFH70" {
        value 359;
        description
          "CR5D0L5XFH70.";
      }
      enum "CR5D0E3MFA70" {
        value 360;
        description
          "CR5D0E3MFA70.";
      }
      enum "CR5D0LAXFH70" {
        value 361;
        description
          "CR5D0LAXFH70.";
      }
      enum "CR57EFGFE2" {
        value 362;
        description
          "CR57EFGFE2.";
      }
      enum "CR57L2XFE2" {
        value 363;
        description
          "CR57L2XFE2.";
      }
      enum "CR57L3XFA2" {
        value 364;
        description
          "CR57L3XFA2.";
      }
      enum "CR57LEXFE01" {
        value 365;
        description
          "CR57LEXFE01.";
      }
      enum "CR57L5XFE2" {
        value 366;
        description
          "CR57L5XFE2.";
      }
      enum "CR57E3MB2" {
        value 367;
        description
          "CR57E3MB2.";
      }
      enum "CR53P1XX0" {
        value 368;
        description
          "CR53P1XX0.";
      }
      enum "CR53P2UF0" {
        value 369;
        description
          "CR53P2UF0.";
      }
      enum "CR53P4UF0" {
        value 370;
        description
          "CR53P4UF0.";
      }
      enum "CR53P4HF0" {
        value 371;
        description
          "CR53P4HF0.";
      }
      enum "CR53P8HF0" {
        value 372;
        description
          "CR53P8HF0.";
      }
      enum "CR58E8NCD" {
        value 373;
        description
          "CR58E8NCD.";
      }
      enum "CR58EFMBD" {
        value 374;
        description
          "CR58EFMBD.";
      }
      enum "CR58EPXFB" {
        value 375;
        description
          "CR58EPXFB.";
      }
      enum "CR56E8NCB" {
        value 376;
        description
          "CR56E8NCB.";
      }
      enum "CR56EFMBB" {
        value 377;
        description
          "CR56EFMBB.";
      }
      enum "CR5D00A2CF70" {
        value 378;
        description
          "CR5D00A2CF70.";
      }
      enum "CR2D00A2CF10" {
        value 379;
        description
          "CR2D00A2CF10.";
      }
      enum "CR56E8NCE" {
        value 380;
        description
          "CR56E8NCE.";
      }
      enum "CR56E2NCC3" {
        value 381;
        description
          "CR56E2NCC3.";
      }
      enum "CR56E8NLDXA" {
        value 382;
        description
          "CR56E8NLDXA.";
      }
      enum "CR56EDNBV" {
        value 383;
        description
          "CR56EDNBV.";
      }
      enum "CR56EDNLIXV" {
        value 384;
        description
          "CR56EDNLIXV.";
      }
      enum "CR2D0E8GFH10" {
        value 385;
        description
          "CR2D0E8GFH10.";
      }
      enum "CR2D0L2XFH11" {
        value 386;
        description
          "CR2D0L2XFH11.";
      }
      enum "CR5D0L2XFH72" {
        value 387;
        description
          "CR5D0L2XFH72.";
      }
      enum "CR5D0E8GFH70" {
        value 388;
        description
          "CR5D0E8GFH70.";
      }
      enum "ME0D0EAGFE70" {
        value 389;
        description
          "ME0D0EAGFE70.";
      }
      enum "ME0D0L2XFE71" {
        value 390;
        description
          "ME0D0L2XFE71.";
      }
      enum "CR5D0L5XFE74" {
        value 391;
        description
          "CR5D0L5XFE74.";
      }
      enum "CR5D0L2XFE75" {
        value 392;
        description
          "CR5D0L2XFE75.";
      }
      enum "CR5D0L5XFE76" {
        value 393;
        description
          "CR5D0L5XFE76.";
      }
      enum "ME0D0EFGFE7E" {
        value 394;
        description
          "ME0D0EFGFE7E.";
      }
      enum "ME0D0L5XXE7E" {
        value 395;
        description
          "ME0D0L5XXE7E.";
      }
      enum "ME0D0L5XXE8E" {
        value 396;
        description
          "ME0D0L5XXE8E.";
      }
      enum "ME0D0L2XXE7E" {
        value 397;
        description
          "ME0D0L2XXE7E.";
      }
      enum "ME0D0L2XFH7H" {
        value 398;
        description
          "ME0D0L2XFH7H.";
      }
      enum "ME0D0L5XFH7H" {
        value 399;
        description
          "ME0D0L5XFH7H.";
      }
      enum "CR57L5XFI3" {
        value 400;
        description
          "CR57L5XFI3.";
      }
      enum "CR57L2XFI2" {
        value 401;
        description
          "CR57L2XFI2.";
      }
      enum "CR5D00E1NC79" {
        value 402;
        description
          "CR5D00E1NC79.";
      }
      enum "CR5D00LAXF71" {
        value 403;
        description
          "CR5D00LAXF71.";
      }
      enum "CR2D00LAXF10" {
        value 404;
        description
          "CR2D00LAXF10.";
      }
      enum "CR2D00E1NC10" {
        value 405;
        description
          "CR2D00E1NC10.";
      }
      enum "CR5D1DMD1M01" {
        value 406;
        description
          "CR5D1DMD1M01.";
      }
      enum "CR5D1DMD1M02" {
        value 407;
        description
          "CR5D1DMD1M02.";
      }
      enum "CR5D1DMD1M03" {
        value 408;
        description
          "CR5D1DMD1M03.";
      }
      enum "CR5D1DMD1M04" {
        value 409;
        description
          "CR5D1DMD1M04.";
      }
      enum "CR5D1DMD1M05" {
        value 410;
        description
          "CR5D1DMD1M05.";
      }
      enum "CR5D1DMD1M06" {
        value 411;
        description
          "CR5D1DMD1M06.";
      }
      enum "CR5D1DMD1M07" {
        value 412;
        description
          "CR5D1DMD1M07.";
      }
      enum "CR5D1DMD1M08" {
        value 413;
        description
          "CR5D1DMD1M08.";
      }
      enum "CR5D2DMD2M01" {
        value 414;
        description
          "CR5D2DMD2M01.";
      }
      enum "CR5D2DMD2M02" {
        value 415;
        description
          "CR5D2DMD2M02.";
      }
      enum "CR5D2DMD2M03" {
        value 416;
        description
          "CR5D2DMD2M03.";
      }
      enum "CR5D2DMD2M04" {
        value 417;
        description
          "CR5D2DMD2M04.";
      }
      enum "CR5D0E2NCE70" {
        value 418;
        description
          "CR5D0E2NCE70.";
      }
      enum "CR5D0LEXFE70" {
        value 419;
        description
          "CR5D0LEXFE70.";
      }
      enum "ME0M0LEXFB70" {
        value 420;
        description
          "ME0M0LEXFB70.";
      }
      enum "ME0M0E2NCB70" {
        value 421;
        description
          "ME0M0E2NCB70.";
      }
      enum "CR57EFGFH2" {
        value 422;
        description
          "CR57EFGFH2.";
      }
      enum "CR5D0EFGFE71" {
        value 423;
        description
          "CR5D0EFGFE71.";
      }
      enum "CR58E8NBA" {
        value 424;
        description
          "CR58E8NBA.";
      }
      enum "CR58D8NCA" {
        value 425;
        description
          "CR58D8NCA.";
      }
      enum "CX68LGXF0" {
        value 426;
        description
          "CX68LGXF0.";
      }
      enum "CR5DE2NLEX60" {
        value 427;
        description
          "CR5DE2NLEX60.";
      }
      enum "CR5D00LFXF60" {
        value 428;
        description
          "CR5D00LFXF60.";
      }
      enum "CR5D00E4NB60" {
        value 429;
        description
          "CR5D00E4NB60.";
      }
      enum "CR56E4NBA1" {
        value 430;
        description
          "CR56E4NBA1.";
      }
      enum "CR5D00N4NC60" {
        value 431;
        description
          "CR5D00N4NC60.";
      }
      enum "CR5D00LMXB60" {
        value 432;
        description
          "CR5D00LMXB60.";
      }
      enum "CR5D0EFGFH70" {
        value 433;
        description
          "CR5D0EFGFH70.";
      }
      enum "ME0D0EFGFH7H" {
        value 434;
        description
          "ME0D0EFGFH7H.";
      }
      enum "CR5D0L2XFH73" {
        value 435;
        description
          "CR5D0L2XFH73.";
      }
      enum "ME0D0L2XFH8H" {
        value 436;
        description
          "ME0D0L2XFH8H.";
      }
      enum "CR5D0L5XFH72" {
        value 437;
        description
          "CR5D0L5XFH72.";
      }
      enum "ME0D0L5XFH8H" {
        value 438;
        description
          "ME0D0L5XFH8H.";
      }
      enum "CR5D0EAGFE70" {
        value 439;
        description
          "CR5D0EAGFE70.";
      }
      enum "CR5D0L2XFE71" {
        value 440;
        description
          "CR5D0L2XFE71.";
      }
      enum "CR5D00LAXF90" {
        value 441;
        description
          "CR5D00LAXF90.";
      }
      enum "CR5D00LEXF6B" {
        value 442;
        description
          "CR5D00LEXF6B.";
      }
      enum "CR5D00E5MF6B" {
        value 443;
        description
          "CR5D00E5MF6B.";
      }
      enum "CR5D00E1NC98" {
        value 444;
        description
          "CR5D00E1NC98.";
      }
      enum "CR2D04OTU210" {
        value 445;
        description
          "CR2D04OTU210.";
      }
      enum "CR2D0E5XMF10" {
        value 446;
        description
          "CR2D0E5XMF10.";
      }
      enum "CR2D00LAXF11" {
        value 447;
        description
          "CR2D00LAXF11.";
      }
      enum "CR2D00E1NC11" {
        value 448;
        description
          "CR2D00E1NC11.";
      }
      enum "CR2D00E2NF10" {
        value 449;
        description
          "CR2D00E2NF10.";
      }
      enum "CR5D00E2NF90" {
        value 450;
        description
          "CR5D00E2NF90.";
      }
      enum "CX6D0E2NBA10" {
        value 451;
        description
          "CX6D0E2NBA10.";
      }
      enum "CX6DE2VE1N10" {
        value 452;
        description
          "CX6DE2VE1N10.";
      }
      enum "ME0M0E2NFB70" {
        value 453;
        description
          "ME0M0E2NFB70.";
      }
      enum "ME0M0E2NFB71" {
        value 454;
        description
          "ME0M0E2NFB71.";
      }
      enum "CR5D00E1NC77" {
        value 455;
        description
          "CR5D00E1NC77.";
      }
      enum "CR5D00E1NC7A" {
        value 456;
        description
          "CR5D00E1NC7A.";
      }
      enum "ME0D0E1NCB70" {
        value 457;
        description
          "ME0D0E1NCB70.";
      }
      enum "ME0D0E1NCB71" {
        value 458;
        description
          "ME0D0E1NCB71.";
      }
      enum "CR57E1NCF2" {
        value 459;
        description
          "CR57E1NCF2.";
      }
      enum "CX6D0E1NCA11" {
        value 460;
        description
          "CX6D0E1NCA11.";
      }
      enum "CR5D00E1ND70" {
        value 461;
        description
          "CR5D00E1ND70.";
      }
      enum "CR5D00E1ND73" {
        value 462;
        description
          "CR5D00E1ND73.";
      }
      enum "ME0D0E1NDB70" {
        value 463;
        description
          "ME0D0E1NDB70.";
      }
      enum "ME0D0E1NDB71" {
        value 464;
        description
          "ME0D0E1NDB71.";
      }
      enum "CX6D0E1NBA10" {
        value 465;
        description
          "CX6D0E1NBA10.";
      }
      enum "CR5D00E2NB60" {
        value 466;
        description
          "CR5D00E2NB60.";
      }
      enum "CR5D00E2NF70" {
        value 467;
        description
          "CR5D00E2NF70.";
      }
      enum "CR5D3DMR4M01" {
        value 468;
        description
          "CR5D3DMR4M01.";
      }
      enum "CR5D3DMR4M02" {
        value 469;
        description
          "CR5D3DMR4M02.";
      }
      enum "CR5DBMC4XV91" {
        value 470;
        description
          "CR5DBMC4XV91.";
      }
      enum "CR5DBMC4XV92" {
        value 471;
        description
          "CR5DBMC4XV92.";
      }
      enum "CR5D00MD8A70" {
        value 472;
        description
          "CR5D00MD8A70.";
      }
      enum "CR2D0EAGFE10" {
        value 473;
        description
          "CR2D0EAGFE10.";
      }
      enum "CR2D0L2XFE10" {
        value 474;
        description
          "CR2D0L2XFE10.";
      }
      enum "CR5D0E2NCE71" {
        value 475;
        description
          "CR5D0E2NCE71.";
      }
      enum "ME0M0E2NCB71" {
        value 476;
        description
          "ME0M0E2NCB71.";
      }
      enum "CR5D0LEXFE71" {
        value 477;
        description
          "CR5D0LEXFE71.";
      }
      enum "CR5D0LEXFE72" {
        value 478;
        description
          "CR5D0LEXFE72.";
      }
      enum "CR5D0LAXFE71" {
        value 479;
        description
          "CR5D0LAXFE71.";
      }
      enum "ME0M0LEXFB71" {
        value 480;
        description
          "ME0M0LEXFB71.";
      }
      enum "CR5D0L6XFH70" {
        value 481;
        description
          "CR5D0L6XFH70.";
      }
      enum "CR5D0L5XFH71" {
        value 482;
        description
          "CR5D0L5XFH71.";
      }
      enum "CX6D0L5XFH11" {
        value 483;
        description
          "CX6D0L5XFH11.";
      }
      enum "ME0D0L5XFH7F" {
        value 484;
        description
          "ME0D0L5XFH7F.";
      }
      enum "ME0D0L6XFH7H" {
        value 485;
        description
          "ME0D0L6XFH7H.";
      }
      enum "ME0D0L6XFE7E" {
        value 486;
        description
          "ME0D0L6XFE7E.";
      }
      enum "CR5D0LBXFH70" {
        value 487;
        description
          "CR5D0LBXFH70.";
      }
      enum "ME0D0LBXFH7H" {
        value 488;
        description
          "ME0D0LBXFH7H.";
      }
      enum "CR5D00N6GF60" {
        value 489;
        description
          "CR5D00N6GF60.";
      }
      enum "CR5D00NBGF60" {
        value 490;
        description
          "CR5D00NBGF60.";
      }
      enum "CR5D00EEGF71" {
        value 491;
        description
          "CR5D00EEGF71.";
      }
      enum "CR2D00EEGF11" {
        value 492;
        description
          "CR2D00EEGF11.";
      }
      enum "CX6D00EEGF10" {
        value 493;
        description
          "CX6D00EEGF10.";
      }
      enum "CR9D00LFXF80" {
        value 494;
        description
          "CR9D00LFXF80.";
      }
      enum "CR9D00NBXF80" {
        value 495;
        description
          "CR9D00NBXF80.";
      }
      enum "CX6D00NBXFA0" {
        value 496;
        description
          "CX6D00NBXFA0.";
      }
      enum "CR9D00N6XF80" {
        value 497;
        description
          "CR9D00N6XF80.";
      }
      enum "CR9D00P8UF80" {
        value 498;
        description
          "CR9D00P8UF80.";
      }
      enum "ANKD001EV106" {
        value 499;
        description
          "ANKD001EV106.";
      }
      enum "CR9D00P4XX80" {
        value 500;
        description
          "CR9D00P4XX80.";
      }
      enum "CR57EFGFH3" {
        value 501;
        description
          "CR57EFGFH3.";
      }
      enum "CR57L6XFI02" {
        value 502;
        description
          "CR57L6XFI02.";
      }
      enum "CR5D0L6XFE70" {
        value 503;
        description
          "CR5D0L6XFE70.";
      }
      enum "CR5D00LFXF76" {
        value 504;
        description
          "CR5D00LFXF76.";
      }
      enum "CR5D00LFXF75" {
        value 505;
        description
          "CR5D00LFXF75.";
      }
      enum "CX6D00LFXF10" {
        value 506;
        description
          "CX6D00LFXF10.";
      }
      enum "ME0D00LFXF70" {
        value 507;
        description
          "ME0D00LFXF70.";
      }
      enum "CR5D00E2NC78" {
        value 508;
        description
          "CR5D00E2NC78.";
      }
      enum "CR5D00E2NC79" {
        value 509;
        description
          "CR5D00E2NC79.";
      }
      enum "CX6D00E2NC10" {
        value 510;
        description
          "CX6D00E2NC10.";
      }
      enum "ME0D00E2NC78" {
        value 511;
        description
          "ME0D00E2NC78.";
      }
      enum "CR5D00E2NF71" {
        value 512;
        description
          "CR5D00E2NF71.";
      }
      enum "CR5D00E2NF72" {
        value 513;
        description
          "CR5D00E2NF72.";
      }
      enum "CX6D00E2NF10" {
        value 514;
        description
          "CX6D00E2NF10.";
      }
      enum "ME0D00E2NF71" {
        value 515;
        description
          "ME0D00E2NF71.";
      }
      enum "CR58EANBB" {
        value 516;
        description
          "CR58EANBB.";
      }
      enum "CR57LBXFE2" {
        value 517;
        description
          "CR57LBXFE2.";
      }
      enum "CR57E8NCB1" {
        value 518;
        description
          "CR57E8NCB1.";
      }
      enum "CR2D00MPAA90" {
        value 519;
        description
          "CR2D00MPAA90.";
      }
      enum "CR2D000SA890" {
        value 520;
        description
          "CR2D000SA890.";
      }
      enum "CR2D00MP8A90" {
        value 521;
        description
          "CR2D00MP8A90.";
      }
      enum "NEDD01MPAA00" {
        value 522;
        description
          "NEDD01MPAA00.";
      }
      enum "NEDD001SA800" {
        value 523;
        description
          "NEDD001SA800.";
      }
      enum "NEDD01MP8A00" {
        value 524;
        description
          "NEDD01MP8A00.";
      }
      enum "NEDD00EX4S00" {
        value 525;
        description
          "NEDD00EX4S00.";
      }
      enum "NEDD001EM600" {
        value 526;
        description
          "NEDD001EM600.";
      }
      enum "CR2D000EM890" {
        value 527;
        description
          "CR2D000EM890.";
      }
      enum "CR5D00E4XF20" {
        value 528;
        description
          "CR5D00E4XF20.";
      }
      enum "CR5D00E1NB20" {
        value 529;
        description
          "CR5D00E1NB20.";
      }
      enum "CR5DE2NE4X10" {
        value 530;
        description
          "CR5DE2NE4X10.";
      }
      enum "CX68E2NLHXF0" {
        value 531;
        description
          "CX68E2NLHXF0.";
      }
      enum "CX68EENEFYFA" {
        value 532;
        description
          "CX68EENEFYFA.";
      }
      enum "CR2D0EM4TP10" {
        value 533;
        description
          "CR2D0EM4TP10.";
      }
      enum "CR5D00T1NC70" {
        value 534;
        description
          "CR5D00T1NC70.";
      }
      enum "CR9D00EANB81" {
        value 535;
        description
          "CR9D00EANB81.";
      }
      enum "CR58EANBA" {
        value 536;
        description
          "CR58EANBA.";
      }
      enum "CR9D00EANB80" {
        value 537;
        description
          "CR9D00EANB80.";
      }
      enum "CR58EENBA0" {
        value 538;
        description
          "CR58EENBA0.";
      }
      enum "CR58D8NCB" {
        value 539;
        description
          "CR58D8NCB.";
      }
      enum "CR58E4KCA0" {
        value 540;
        description
          "CR58E4KCA0.";
      }
      enum "CR58D8NCB0" {
        value 541;
        description
          "CR58D8NCB0.";
      }
      enum "CR9D00D8KC80" {
        value 542;
        description
          "CR9D00D8KC80.";
      }
      enum "CR57EENBE0" {
        value 543;
        description
          "CR57EENBE0.";
      }
      enum "CR5DE2VE1N70" {
        value 544;
        description
          "CR5DE2VE1N70.";
      }
      enum "CR5D0E5XMF90" {
        value 545;
        description
          "CR5D0E5XMF90.";
      }
      enum "CR58E4KE4NA0" {
        value 546;
        description
          "CR58E4KE4NA0.";
      }
      enum "CR5D00E8NC64" {
        value 547;
        description
          "CR5D00E8NC64.";
      }
      enum "CR5D00E8NB61" {
        value 548;
        description
          "CR5D00E8NB61.";
      }
      enum "CR5D00E8NB63" {
        value 549;
        description
          "CR5D00E8NB63.";
      }
      enum "CR5D00E2KC61" {
        value 550;
        description
          "CR5D00E2KC61.";
      }
      enum "CR5D00E8NC65" {
        value 551;
        description
          "CR5D00E8NC65.";
      }
      enum "CR5D00LJXF61" {
        value 552;
        description
          "CR5D00LJXF61.";
      }
      enum "CR5D00LJXF60" {
        value 553;
        description
          "CR5D00LJXF60.";
      }
      enum "CR5D00E4NB63" {
        value 554;
        description
          "CR5D00E4NB63.";
      }
      enum "CR5D00LFXF63" {
        value 555;
        description
          "CR5D00LFXF63.";
      }
      enum "CR5D00E2NC63" {
        value 556;
        description
          "CR5D00E2NC63.";
      }
      enum "CR5D00LEXF65" {
        value 557;
        description
          "CR5D00LEXF65.";
      }
      enum "CR5D00E2KC60" {
        value 558;
        description
          "CR5D00E2KC60.";
      }
      enum "CARD ATN 905" {
        value 559;
        description
          "CARD ATN 905.";
      }
      enum "CARD ATN 910C-F" {
        value 560;
        description
          "CARD ATN 910C-F.";
      }
      enum "CARD ATN 910C-E" {
        value 561;
        description
          "CARD ATN 910C-E.";
      }
      enum "CR5D00N8NC61" {
        value 562;
        description
          "CR5D00N8NC61.";
      }
      enum "CR5D00N8NC60" {
        value 563;
        description
          "CR5D00N8NC60.";
      }
      enum "CARD ETN500-F" {
        value 564;
        description
          "CARD ETN500-F.";
      }
      enum "CARD NE05E-SR" {
        value 565;
        description
          "CARD NE05E-SR.";
      }
      enum "CR5D04OTU290" {
        value 566;
        description
          "CR5D04OTU290.";
      }
      enum "CR5D00P4XX60" {
        value 567;
        description
          "CR5D00P4XX60.";
      }
      enum "CR9D00N2NC80" {
        value 568;
        description
          "CR9D00N2NC80.";
      }
      enum "CX6D00N2NCA0" {
        value 569;
        description
          "CX6D00N2NCA0.";
      }
      enum "CR5D00E2NC77" {
        value 570;
        description
          "CR5D00E2NC77.";
      }
      enum "UNKNOWN_SUBCARD" {
        value 571;
        description
          "UNKNOWN_SUBCARD.";
      }
      enum "ANDD16E11202" {
        value 572;
        description
          "ANDD16E11202.";
      }
      enum "ANDD16E17502" {
        value 573;
        description
          "ANDD16E17502.";
      }
      enum "ANDD32E11202" {
        value 574;
        description
          "ANDD32E11202.";
      }
      enum "ANDD32E17502" {
        value 575;
        description
          "ANDD32E17502.";
      }
      enum "ANDD000EX2S0" {
        value 576;
        description
          "ANDD000EX2S0.";
      }
      enum "ANDD000EX1S0" {
        value 577;
        description
          "ANDD000EX1S0.";
      }
      enum "ANJ1EXL1" {
        value 578;
        description
          "ANJ1EXL1.";
      }
      enum "ANDD00EM4T01" {
        value 579;
        description
          "ANDD00EM4T01.";
      }
      enum "ANDD00EM8T01" {
        value 580;
        description
          "ANDD00EM8T01.";
      }
      enum "ANDD00EM4F01" {
        value 581;
        description
          "ANDD00EM4F01.";
      }
      enum "ANDD00EM8F01" {
        value 582;
        description
          "ANDD00EM8F01.";
      }
      enum "ANKD00EX2S00" {
        value 583;
        description
          "ANKD00EX2S00.";
      }
      enum "NEDD00EM4F01" {
        value 584;
        description
          "NEDD00EM4F01.";
      }
      enum "NEDD00EM4T01" {
        value 585;
        description
          "NEDD00EM4T01.";
      }
      enum "NEDD00EM8F01" {
        value 586;
        description
          "NEDD00EM8F01.";
      }
      enum "NEDD00EM8T01" {
        value 587;
        description
          "NEDD00EM8T01.";
      }
      enum "NEDD000EX1S0" {
        value 588;
        description
          "NEDD000EX1S0.";
      }
      enum "NEDD00EX2S00" {
        value 589;
        description
          "NEDD00EX2S00.";
      }
      enum "NEDD32E17501" {
        value 590;
        description
          "NEDD32E17501.";
      }
      enum "NEDD32E11201" {
        value 591;
        description
          "NEDD32E11201.";
      }
      enum "ANJD01XE8F00" {
        value 592;
        description
          "ANJD01XE8F00.";
      }
      enum "CARD ATN 910C-A" {
        value 593;
        description
          "CARD ATN 910C-A.";
      }
      enum "CARD ATN 910C-B" {
        value 594;
        description
          "CARD ATN 910C-B.";
      }
      enum "CARD NE05E-SQ" {
        value 595;
        description
          "CARD NE05E-SQ.";
      }
      enum "LNDD01XE8F00" {
        value 596;
        description
          "LNDD01XE8F00.";
      }
      enum "ANKD00EX4S00" {
        value 597;
        description
          "ANKD00EX4S00.";
      }
      enum "ANKD00EM20F0" {
        value 598;
        description
          "ANKD00EM20F0.";
      }
      enum "ANKD0EM20F00" {
        value 599;
        description
          "ANKD0EM20F00.";
      }
      enum "CARD ATN 910C-H" {
        value 600;
        description
          "CARD ATN 910C-H:";
      }
      enum "CARD1 ATN 910C-D" {
        value 601;
        description
          "CARD1 ATN 910C-D.";
      }
      enum "ANG2MO1" {
        value 602;
        description
          "ANG2MO1.";
      }
      enum "ANDD00CQ1B00" {
        value 603;
        description
          "ANDD00CQ1B00.";
      }
      enum "NEDD16E17502" {
        value 604;
        description
          "NEDD16E17502.";
      }
      enum "NEDD16E11202" {
        value 605;
        description
          "NEDD16E11202.";
      }
      enum "NEDD16E17501" {
        value 606;
        description
          "NEDD16E17501.";
      }
      enum "NEDD16E11201" {
        value 607;
        description
          "NEDD16E11201.";
      }
      enum "NEDD00CQ1B00" {
        value 608;
        description
          "NEDD00CQ1B00.";
      }
      enum "ANKD001EV200" {
        value 609;
        description
          "ANKD001EV200.";
      }
      enum "ANKD01EXAS00" {
        value 610;
        description
          "ANKD01EXAS00.";
      }
      enum "ANKD001EV100" {
        value 611;
        description
          "ANKD001EV100.";
      }
      enum "ANKD001EH100" {
        value 612;
        description
          "ANKD001EH100.";
      }
      enum "CX6D00E2XF70" {
        value 613;
        description
          "CX6D00E2XF70.";
      }
      enum "CR57E1NBA2" {
        value 614;
        description
          "CR57E1NBA2.";
      }
      enum "CR57LAXFE01" {
        value 615;
        description
          "CR57LAXFE01.";
      }
      enum "CR57E2NCF1" {
        value 616;
        description
          "CR57E2NCF1.";
      }
      enum "CX6D0E2NCA11" {
        value 617;
        description
          "CX6D0E2NCA11.";
      }
      enum "ME0M0E2NCB72" {
        value 618;
        description
          "ME0M0E2NCB72.";
      }
      enum "CR57E2NBB2" {
        value 619;
        description
          "CR57E2NBB2.";
      }
      enum "CR5D0E2NFE70" {
        value 620;
        description
          "CR5D0E2NFE70.";
      }
      enum "CARD ATN 910B-A" {
        value 621;
        description
          "CARD ATN 910B-A.";
      }
      enum "CARD ATN 910B-B" {
        value 622;
        description
          "CARD ATN 910B-B.";
      }
      enum "CARD ATN 910B-D" {
        value 623;
        description
          "CARD ATN 910B-D.";
      }
      enum "CARD ATN 910B-E" {
        value 624;
        description
          "CARD ATN 910B-E.";
      }
      enum "CARD ATN 910B-F" {
        value 625;
        description
          "CARD ATN 910B-F.";
      }
      enum "CARD NE05E-S2" {
        value 626;
        description
          "CARD NE05E-S2.";
      }
      enum "CR57L6XE4GF0" {
        value 627;
        description
          "CR57L6XE4GF0.";
      }
      enum "CR57E4GFC0" {
        value 628;
        description
          "CR57E4GFC0.";
      }
      enum "NEDD32E1M001" {
        value 629;
        description
          "NEDD32E1M001.";
      }
      enum "ANDD0032E100" {
        value 630;
        description
          "ANDD0032E100.";
      }
      enum "ANDD00EM8F00" {
        value 631;
        description
          "ANDD00EM8F00.";
      }
      enum "ANDD00EM8T00" {
        value 632;
        description
          "ANDD00EM8T00.";
      }
      enum "ANDD00EM4F00" {
        value 633;
        description
          "ANDD00EM4F00.";
      }
      enum "ANDD00EM4T00" {
        value 634;
        description
          "ANDD00EM4T00.";
      }
      enum "ANDD000EX100" {
        value 635;
        description
          "ANDD000EX100.";
      }
      enum "ANDD00EM8M00" {
        value 636;
        description
          "ANDD00EM8M00.";
      }
      enum "NEDD00EF8T00" {
        value 637;
        description
          "NEDD00EF8T00.";
      }
      enum "NEDD000EG400" {
        value 638;
        description
          "NEDD000EG400.";
      }
      enum "NEDD00EG4T00" {
        value 639;
        description
          "NEDD00EG4T00.";
      }
      enum "NEDD0EM4TP00" {
        value 640;
        description
          "NEDD0EM4TP00.";
      }
      enum "CR9D00LFXF81" {
        value 641;
        description
          "CR9D00LFXF81.";
      }
      enum "CR5D00E4XF25" {
        value 642;
        description
          "CR5D00E4XF25.";
      }
      enum "ANKD001EY200" {
        value 643;
        description
          "ANKD001EY200.";
      }
      enum "ANKD001EY400" {
        value 644;
        description
          "ANKD001EY400.";
      }
      enum "CX6D0LEXFA12" {
        value 645;
        description
          "CX6D0LEXFA12.";
      }
      enum "CX6D0E2NCA12" {
        value 646;
        description
          "CX6D0E2NCA12.";
      }
      enum "CR5D0E2NBE71" {
        value 647;
        description
          "CR5D0E2NBE71.";
      }
      enum "CR5D00LEXF74" {
        value 648;
        description
          "CR5D00LEXF74.";
      }
      enum "CR5D00LEXF73" {
        value 649;
        description
          "CR5D00LEXF73.";
      }
      enum "CX6D00LEXF10" {
        value 650;
        description
          "CX6D00LEXF10.";
      }
      enum "ME0D00LEXF70" {
        value 651;
        description
          "ME0D00LEXF70.";
      }
      enum "CX6D00E4XF25" {
        value 652;
        description
          "CX6D00E4XF25.";
      }
      enum "CX6D0E5XMF90" {
        value 653;
        description
          "CX6D0E5XMF90.";
      }
      enum "CX6D00E4XF20" {
        value 654;
        description
          "CX6D00E4XF20.";
      }
      enum "CX6D00E1NB20" {
        value 655;
        description
          "CX6D00E1NB20.";
      }
      enum "CX6DE2NE4X12" {
        value 656;
        description
          "CX6DE2NE4X12.";
      }
      enum "CX6D00E1NC98" {
        value 657;
        description
          "CX6D00E1NC98.";
      }
      enum "CX6D00LAXF90" {
        value 658;
        description
          "CX6D00LAXF90.";
      }
      enum "CX6D0L2XFE71" {
        value 659;
        description
          "CX6D0L2XFE71.";
      }
      enum "ANKD001EY401" {
        value 660;
        description
          "ANKD001EY401.";
      }
      enum "ANKD001EV102" {
        value 661;
        description
          "ANKD001EV102.";
      }
      enum "ANKD001EV103" {
        value 662;
        description
          "ANKD001EV103.";
      }
      enum "ANKD001EV105" {
        value 663;
        description
          "ANKD001EV105.";
      }
      enum "ANKD001EV104" {
        value 664;
        description
          "ANKD001EV104.";
      }
      enum "CR2D0E5XMF91" {
        value 665;
        description
          "CR2D0E5XMF91.";
      }
      enum "CR2D00E4XM25" {
        value 666;
        description
          "CR2D00E4XM25.";
      }
      enum "CR2D00E8XM25" {
        value 667;
        description
          "CR2D00E8XM25.";
      }
      enum "CR2D00LAXF91" {
        value 668;
        description
          "CR2D00LAXF91.";
      }
      enum "CR2DE2NE4X10" {
        value 669;
        description
          "CR2DE2NE4X10.";
      }
      enum "CR2D00E4XF20" {
        value 670;
        description
          "CR2D00E4XF20.";
      }
      enum "CR2D00E1NB20" {
        value 671;
        description
          "CR2D00E1NB20.";
      }
      enum "ANKD001EV201" {
        value 672;
        description
          "ANKD001EV201.";
      }
      enum "ANKD01EXAS01" {
        value 673;
        description
          "ANKD01EXAS01.";
      }
      enum "ANKD001EY201" {
        value 674;
        description
          "ANKD001EY201.";
      }
      enum "ANKD001EY100" {
        value 675;
        description
          "ANKD001EY100.";
      }
      enum "CR5D0E5XMF91" {
        value 676;
        description
          "CR5D0E5XMF91.";
      }
      enum "CR5D0E5XMF93" {
        value 677;
        description
          "CR5D0E5XMF93.";
      }
      enum "CR5D0E5XMF94" {
        value 678;
        description
          "CR5D0E5XMF94.";
      }
      enum "CR5DE2NE4X13" {
        value 679;
        description
          "CR5DE2NE4X13.";
      }
      enum "CR5DE2NE4X14" {
        value 680;
        description
          "CR5DE2NE4X14.";
      }
      enum "ANKD001EV202" {
        value 681;
        description
          "ANKD001EV202.";
      }
      enum "CR5D00E4XM25" {
        value 682;
        description
          "CR5D00E4XM25.";
      }
      enum "CR5D00L4XF91" {
        value 683;
        description
          "CR5D00L4XF91:";
      }
      enum "CR5D00EAGF96" {
        value 684;
        description
          "CR5D00EAGF96:";
      }
      enum "CR2D0E5XMF93" {
        value 685;
        description
          "CR2D0E5XMF93:";
      }
      enum "CR5D00E8XM25" {
        value 686;
        description
          "CR5D00E8XM25.";
      }
      enum "CR5D00LAXF91" {
        value 687;
        description
          "CR5D00LAXF91.";
      }
      enum "CX6D0E5XMF91" {
        value 688;
        description
          "CX6D0E5XMF91.";
      }
      enum "CX6D00E4XF91" {
        value 689;
        description
          "CX6D00E4XF91.";
      }
      enum "CX6D00E8XF91" {
        value 690;
        description
          "CX6D00E8XF91.";
      }
      enum "CX6D00LAXF91" {
        value 691;
        description
          "CX6D00LAXF91.";
      }
      enum "CR5DE4VE2N70" {
        value 692;
        description
          "CR5DE4VE2N70.";
      }
      enum "CR57E4VBE1" {
        value 693;
        description
          "CR57E4VBE1.";
      }
      enum "CR57E8VBA1" {
        value 694;
        description
          "CR57E8VBA1.";
      }
      enum "CR57EDYFA1" {
        value 695;
        description
          "CR57EDYFA1.";
      }
      enum "CR57EENBC0" {
        value 696;
        description
          "CR57EENBC0.";
      }
      enum "CR57EENBC1" {
        value 697;
        description
          "CR57EENBC1.";
      }
      enum "CR58EENBD0" {
        value 698;
        description
          "CR58EENBD0.";
      }
      enum "CX6DE4VE2N10" {
        value 699;
        description
          "CX6DE4VE2N10.";
      }
      enum "CR9D00LJXF80" {
        value 700;
        description
          "CR9D00LJXF80.";
      }
      enum "CR9D00EANB82" {
        value 701;
        description
          "CR9D00EANB82.";
      }
      enum "CR9D00E5NB80" {
        value 702;
        description
          "CR9D00E5NB80.";
      }
      enum "CR9D00EDYF80" {
        value 703;
        description
          "CR9D00EDYF80.";
      }
      enum "CR59T8NBB" {
        value 704;
        description
          "CR59T8NBB.";
      }
      enum "CR59E2KBA" {
        value 705;
        description
          "CR59E2KBA.";
      }
      enum "CR59LJXFC" {
        value 706;
        description
          "CR59LJXFC.";
      }
      enum "CR58E8NBE" {
        value 707;
        description
          "CR58E8NBE.";
      }
      enum "CR59E8NBE" {
        value 708;
        description
          "CR59E8NBE.";
      }
      enum "CR59E2KCA1" {
        value 709;
        description
          "CR59E2KCA1.";
      }
      enum "CR58E4KE4NB0" {
        value 710;
        description
          "CR58E4KE4NB0.";
      }
      enum "CX6D0E2NBA11" {
        value 711;
        description
          "CX6D0E2NBA11.";
      }
      enum "CX6D0LAXFA13" {
        value 712;
        description
          "CX6D0LAXFA13.";
      }
      enum "CARD ATN 910C-S" {
        value 713;
        description
          "CARD ATN 910C-S.";
      }
      enum "CR5D00P4CFC1" {
        value 714;
        description
          "CR5D00P4CFC1.";
      }
      enum "CR5D000DE1C1" {
        value 715;
        description
          "CR5D000DE1C1.";
      }
      enum "CR5D00C4CFC1" {
        value 716;
        description
          "CR5D00C4CFC1.";
      }
      enum "ANND16E17500" {
        value 717;
        description
          "ANND16E17500.";
      }
      enum "ANND00CQ1B00" {
        value 718;
        description
          "ANND00CQ1B00.";
      }
      enum "CR5D00EAGF95" {
        value 719;
        description
          "CR5D00EAGF95.";
      }
      enum "CR57E8YFA1" {
        value 720;
        description
          "CR57E8YFA1.";
      }
      enum "CARD ATN 910C-G" {
        value 721;
        description
          "CARD ATN 910C-G.";
      }
      enum "CR58EPYFA00" {
        value 722;
        description
          "CR58EPYFA00.";
      }
      enum "CR59EENBD0" {
        value 723;
        description
          "CR59EENBD0.";
      }
      enum "CR59LPXFA0" {
        value 724;
        description
          "CR59LPXFA0.";
      }
      enum "GPLI40CQES1" {
        value 725;
        description
          "GPLI40CQES1.";
    }
      enum "GPLI72YSES1" {
        value 726;
    description
          "GPLI72YSES1.";
      }
      enum "GPLI8KQ8CQE1" {
        value 727;
        description
          "GPLI8KQ8CQE1.";
      }
      enum "CR2D00E2NB00" {
        value 728;
        description
          "CR2D00E2NB00.";
    }
      enum "CX6DE8VE4N10" {
        value 729;
        description
          "CX6DE8VE4N10.";
    }
      enum "CARD NetEngine 8000 M1A" {
        value 730;
        description
          "CARD NetEngine 8000 M1A.";
    }
     enum "CX62E2NBB00" {
        value 731;
        description
          "CX62E2NBB00.";
      }
     enum "CX62LEXFC00" {
        value 732;
        description
          "CX62LEXFC00.";
      }
     enum "CR5DE8VE4N70" {
        value 733;
        description
          "CR5DE8VE4N70.";
      }
     enum "ANND0EM10F00" {
        value 734;
        description
          "ANND0EM10F00.";
      }
      enum "ANND0EM20F00" {
        value 735;
        description
          "ANND0EM20F00.";
      }
     enum "CR5D00EEGF73" {
        value 736;
        description
          "CR5D00EEGF73.";
      }
      enum "CR5D00E1NC97" {
        value 737;
        description
          "CR5D00E1NC97.";
      }
    enum "GPLI40CQE2" {
        value 738;
        description
          "GPLI40CQE2.";
      }
    enum "GPLI72YSE2" {
        value 739;
        description
          "GPLI72YSE2.";
      }
      enum "CR5D00C8CF72" {
        value 740;
        description
          "CR5D00C8CF72.";
      }
      enum "CR5D00P8CF70" {
        value 741;
        description
          "CR5D00P8CF70.";
      }
      enum "CR5D00CFE170" {
        value 742;
        description
          "CR5D00CFE170.";
      }
      enum "CR8D00E1VBC0" {
        value 751;
        description
          "CR8D00E1VBC0.";
      }
      enum "CR8D25E2XFC0" {
        value 752;
        description
          "CR8D25E2XFC0.";
      }
      enum "CR8D00L4XFC0" {
        value 753;
        description
          "CR8D00L4XFC0.";
      }
      enum "CR8D00E2XFC0" {
        value 754;
        description
          "CR8D00E2XFC0.";
      }
      enum "CR8D00EAGFC0" {
        value 755;
        description
          "CR8D00EAGFC0.";
      }
      enum "CR8D00EEGFC0" {
        value 756;
        description
          "CR8D00EEGFC0.";
      }
      enum "CR58EENBD1" {
        value 789;
        description
          "CR58EENBD1.";
      }
      enum "CR8D00E1NBC1" {
        value 790;
        description
          "CR8D00E1NBC1.";
      }
      enum "CR8D00E2VBC1" {
        value 791;
        description
          "CR8D00E2VBC1.";
      }
      enum "CR8D00E2NBC1" {
        value 792;
        description
          "CR8D00E2NBC1.";
      }
    }
    description
      "Hardware-subcard-type.";
  }
}
