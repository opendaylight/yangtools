/*
Copyright (C) 2019 Huawei Technologies Co., Ltd. All rights reserved.
*/
module huawei-bras-auto-save-deviations-CH-NE-X3 {
  namespace "urn:huawei:yang:huawei-bras-auto-save-deviations-CH-NE-X3";
  prefix bras-auto-save-devs-CH-NE-X3;

  import huawei-bras-auto-save {
    prefix bras-auto-save;
  }

  organization
    "Huawei Technologies Co., Ltd.";
  contact
    "Huawei Industrial Base
     Bantian, Longgang
     Shenzhen 518129
     People's Republic of China
     Website: http://www.huawei.com
     Email: support@huawei.com";
  description
    "Global Configuration.";

  revision 2019-09-25 {
    description
      "Init revision.";
    reference "Huawei private.";
  }
  deviation "/bras-auto-save:bras-auto-save/bras-auto-save:auto-save-max-user/bras-auto-save:number" {
    deviate replace {
      type uint32 {
        range "8000..128000";
      }
    }
  }
}
