/*
Copyright (C) 2019 Huawei Technologies Co., Ltd. All rights reserved.
*/
module huawei-lldp-deviations-CH-NE-X3 {
  namespace "urn:huawei:yang:huawei-lldp-deviations-CH-NE-X3";
  prefix lldp-devs-CH-NE-X3;

  import huawei-ifm {
    prefix ifm;
  }
  import huawei-lldp {
    prefix lldp;
  }

  organization
    "Huawei Technologies Co., Ltd.";
  contact
    "Huawei Industrial Base
     Bantian, Longgang
     Shenzhen 518129
     People's Republic of China
     Website: http://www.huawei.com
     Email: support@huawei.com";
  description
    "Link layer discovery protocol.";

  revision 2019-04-23 {
    description
      "Initial revision.";
    reference "Huawei private.";
  }

  deviation "/ifm:ifm/ifm:interfaces/ifm:interface/lldp:lldp/lldp:session/lldp:tlv-enable/lldp:ddp" {
    deviate not-supported;
  }
}
