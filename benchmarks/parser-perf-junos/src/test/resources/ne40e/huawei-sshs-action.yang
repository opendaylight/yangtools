/*
Copyright (C) 2013-2017 Huawei Technologies Co., Ltd. All rights reserved.
*/
submodule huawei-sshs-action {
  belongs-to huawei-sshs {
    prefix sshs;
  }
  import ietf-inet-types {
    prefix inet;
  }
  import huawei-extension {
    prefix ext;
  }
  organization
    "Huawei Technologies Co.,Ltd.";
  contact
    "Huawei Industrial Base Bantian, Longgang Shenzhen 518129                    
        People's Republic of China                    
        Website: http://www.huawei.com Email: support@huawei.com";
  description
    "Description of ssh server action submodule";
  revision 2017-03-23 {
    description
      "Functions supported by the schema are added to the YANG file.";
    reference
      "Huawei private.";
  }
  revision 2013-01-01 {
    description
      "Init revision";
    reference    "Huawei private.";
  }
  rpc activateIps {
    description
      "Activate";
    input {
      list activateIp {
        description
          "Activate IPs";
        leaf ipAddress {
          type inet:ip-address-no-zone;
          mandatory true;
          description
            "IP Address";
          ext:allowDelete "false";
        }
        leaf vpnName {
          type string {
            length "1..31";
          }
          description
            "VPN Name";
          ext:allowDelete "true";
        }
      }
    }
  }
}
