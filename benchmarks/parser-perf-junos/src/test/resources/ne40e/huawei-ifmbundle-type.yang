/*
Copyright (C) 2013-2017 Huawei Technologies Co., Ltd. All rights reserved.
*/
submodule huawei-ifmbundle-type {
  belongs-to huawei-ifmbundle {
    prefix ifmbundle;
  }
  
  organization
    "Huawei Technologies Co.,Ltd.";
  contact
    "Huawei Industrial Base Bantian, Longgang Shenzhen 518129                    
        People's Republic of China                    
        Website: http://www.huawei.com Email: support@huawei.com";
  description
    "the ifmbundle type submodule";
  revision 2017-03-23 {
    description
      "Functions supported by the schema are added to the YANG file.";
    reference
      "Huawei private.";
  }
  revision 2013-01-01 {
    description
      "Init revision";
    reference
      "Huawei private.";
  }

  typedef ifmbundleAbstractState {
    type enumeration {
      enum "Up" {
        description
          "The interface is in the Up state.";
      }
      enum "Down" {
        description
          "The interface is in the Down state.";
      }
    }
    description
      "Atm-bundle Inteface Abstract State";
  }
}
