/*
Copyright (C) 2013-2017 Huawei Technologies Co., Ltd. All rights reserved.
*/
submodule huawei-dhcpv6-type {
  belongs-to huawei-dhcpv6 {
    prefix dhcpv6;
  }
  
  organization
    "Huawei Technologies Co.,Ltd.";
  contact
    "Huawei Industrial Base Bantian, Longgang Shenzhen 518129                    
        People's Republic of China                    
        Website: http://www.huawei.com Email: support@huawei.com";
  description
    "test.Description FOR submodule";
  revision 2017-03-23 {
    description
      "Functions supported by the schema are added to the YANG file.";
    reference
      "Huawei private.";
  }
  revision 2013-01-01 {
    description
      "Init revision";
    reference
      "Huawei private.";
  }
  typedef dhcpv6Duid {
    type enumeration {
      enum "invalid" {
        description
          "-";
      }
      enum "llt" {
        description
          "Link-layer address plus time.";
      }
      enum "user-defined" {
        description
          "User-defined.";
      }
    }
    description
      "description of dhcp6_dhcpv6Duid_type";
  }
  typedef dhcpv6RemoteIdFormat {
    type enumeration {
      enum "default" {
        description
          "Default.";
      }
      enum "user-defined" {
        description
          "User-defined.";
      }
    }
    description
      "description of dhcp6_dhcpv6RemoteIdFormat_type";
  }
}
