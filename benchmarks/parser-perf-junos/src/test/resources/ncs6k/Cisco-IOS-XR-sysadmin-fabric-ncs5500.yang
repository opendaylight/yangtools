module Cisco-IOS-XR-sysadmin-fabric-ncs5500 {
  namespace "http://www.cisco.com/ns/yang/Cisco-IOS-XR-sysadmin-fabric";
  prefix fabric;

  import tailf-common {
    prefix tailf;
  }
  import Cisco-IOS-XR-sysadmin-fabric-mgr-fgid {
    prefix fabric-fgid;
  }
  import Cisco-IOS-XR-sysadmin-fabric-mgr-fsdb-server-ncs5500 {
    prefix fabric-fsdb;
  }
  import Cisco-IOS-XR-sysadmin-fabric-mgr-fsdb-aggregator-ncs5500 {
    prefix fabric_fsdb_aggr;

  }
  import Cisco-IOS-XR-sysadmin-fabric-driver-sfe {
    prefix fabric-sfe;
  }

  revision 2017-05-01 {
    description
      "Namespace change to comply with Cisco guidelines on namespace";
  }

  grouping fabric_action_cmds {
    container fabric_action {
      tailf:cli-drop-node-name;
      tailf:cli-suppress-show-path;
      container fabric {
        description
          "Fabric resource commands";
        tailf:info "Fabric resource commands";
        tailf:cli-suppress-show-path;
        uses fabric_fsdb_aggr:fsdb_aggr_ppu;
      }
    }
  }

  grouping fabric_clear {
    container fabric {
      description
        "Fabric resource commands";
      tailf:info "Fabric resource commands";
      tailf:cli-incomplete-show-path;
      uses fabric_fsdb_aggr:fsdb_aggr_clear;
    }
  }

  grouping fabric {
    container fabric {
      description
        "Fabric resource commands";
      tailf:info "Fabric resource commands";
      tailf:cli-drop-node-name;
      container fabric {
        description
          "Fabric configuration";
        tailf:info "Fabric configuration";
        container fsdbagg {
          tailf:cli-drop-node-name;
          uses fabric_fsdb_aggr:fsdb_agg_conf_plane;
        }
        uses fabric-fgid:fgid_conf_resource;
      }
      container oper {
        config false;
        tailf:callpoint "fabric_oper";
        tailf:cli-incomplete-show-path;
        tailf:cli-drop-node-name;
        tailf:hidden "internal-command";
        uses fabric-fgid:fgid;
        uses fabric_fsdb_aggr:fsdb_aggr;
        uses fabric-fsdb:fsdb_svr;
      }
    }
    container sfe_oper {
      config false;
      tailf:callpoint "fabric_oper";
      tailf:cli-incomplete-show-path;
      tailf:cli-drop-node-name;
      uses fabric-sfe:sfe;
    }
  }
  tailf:id "http://www.cisco.com/panini/calvados/fabric";
}
