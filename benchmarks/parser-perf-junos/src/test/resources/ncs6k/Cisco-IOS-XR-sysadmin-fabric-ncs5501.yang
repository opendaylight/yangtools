module Cisco-IOS-XR-sysadmin-fabric-ncs5501 {
  namespace "http://www.cisco.com/ns/yang/Cisco-IOS-XR-sysadmin-fabric-ncs5501";
  prefix fabric;

  import tailf-common {
    prefix tailf;
  }
  import Cisco-IOS-XR-sysadmin-fabric-mgr-fgid {
    prefix fabric-fgid;
  }

  revision 2017-05-01 {
    description
      "Namespace change to comply with Cisco guidelines on namespace";
  }

  grouping fabric {
    container fabric {
      description
        "Fabric resource commands";
      tailf:info "Fabric resource commands";
      tailf:cli-drop-node-name;
      container oper {
        config false;
        tailf:callpoint "fabric_oper";
        tailf:cli-incomplete-show-path;
        tailf:cli-drop-node-name;
        tailf:hidden "internal-command";
        uses fabric-fgid:fgid;
      }
    }
  }
  tailf:id "http://www.cisco.com/panini/calvados/fabric";
}
