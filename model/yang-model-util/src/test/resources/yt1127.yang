module foo {
  namespace foo;
  prefix foo;

  grouping grp {
    leaf leaf1 {
      type leafref {
        path "../../foo:foo_cont/foo:name";
      }
    }
  }
  container cont {
    leaf leaf2 {
       type leafref {
        path "../../../foo:foo_cont/foo:name";
      }
    }
  }
}
