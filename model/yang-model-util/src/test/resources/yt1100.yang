module yt1100 {
  yang-version 1.1;
  namespace "a";
  prefix a;

  container foo {
    list scheduler-node {
      key "name";
      leaf name {
        type string;
      }
      choice children-type {
        case scheduler-node {
          list child-scheduler-nodes {
            key "name";
            leaf name {
              type leafref {
                  path '../../../a:scheduler-node/a:name';
              }
            }
          }
        }
      }
    }
  }
}
