module foo {
  namespace foo;
  prefix foo;

  container foo {
    choice foo {
      case foo {
        leaf foo {
          type leafref {
            path ../../bar;
          }
        }
      }
    }
  }

  leaf bar {
    type string;
  }
}
