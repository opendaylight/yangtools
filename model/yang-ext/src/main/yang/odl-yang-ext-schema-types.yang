module odl-yang-ext-schema-types {
	yang-version 1;
    namespace "urn:opendaylight:params:ns:yang:extension:schema:semantic";
    prefix "ext-schema";
    
    contact "Anton Tkacik <ttkacik@cisco.com>";

    description 
            "Copyright (c) 2014 Cisco Systems, Inc. and others.  All rights reserved.

            This program and the accompanying materials are made available under the
            terms of the Eclipse Public License v1.0 which accompanies this distribution,
            and is available at http://www.eclipse.org/legal/epl-v10.html";



	typedef type-definition {
    	// FIXME: Define proper type
        type string;
    }

    typedef statement-or-extension {
        // FIXME: Define proper type
        type string;
    }

	// Schema paths

	typedef descendant-schema-nodeid {
		type string;
	}

	typedef absolute-schema-nodeid {
		type string;
	}

	typedef schema-nodeid {
		type union {
			type descendant-schema-nodeid;
			type absolute-schema-nodeid;
		}
	}

	typedef leafref-path {
		// FIXME: yang:xpath1.0
		type string;
	}
}
