module leafref-yang1 {
    namespace leafref-yang1;
    prefix lr;
    yang-version 1;

    leaf my-leafref-3 {
        type leafref {
            path "/target";
        }
        status current;
        mandatory true;
        config false;
    }

    leaf target {
        type string;
    }
}
