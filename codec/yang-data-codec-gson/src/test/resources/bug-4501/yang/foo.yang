module foo {
    namespace "foo";
    prefix foo;
    yang-version 1;

    list hop {
        leaf address {
            type string;
        }

        leaf lrs-bits {
            type bits {
                bit lookup {
                    description
                                        "Lookup bit.";
                }
                bit rloc-probe {
                    description
                                        "RLOC-probe bit.";
                }
                bit strict {
                    description
                                        "Strict bit.";
                }
            }
            description
                        "Flag bits per hop.";
        }
    }
}
