module bar {
  namespace barns;
  prefix bar;

  import foo { prefix foo; }

  identity two {
    base foo:one;
  }

  leaf-list str {
    type string;
  }

  leaf-list foo {
    type identityref {
      base foo:one;
    }
  }

  leaf-list bar {
    type instance-identifier;
  }

  leaf-list bee {
    type foo:bitz;
  }

  leaf baz {
    type instance-identifier;
  }
}
