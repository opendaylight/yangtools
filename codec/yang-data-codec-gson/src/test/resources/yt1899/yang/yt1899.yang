module yt1899 {
  namespace yt1899;
  prefix yt1899;

  container top {
    list foo {
      key name;

      leaf name {
        type string;
      }

      choice bar {
        case baz {
          leaf baz-leaf {
            type string;
          }
        }
      }
    }
  }

  grouping grp {
    container grp-cont {
      leaf grp-leaf {
        type string;
      }

      choice grp-choice {
        case grp-case {
          leaf grp-case-leaf {
            type string;
          }
        }
      }
    }
  }

  rpc thud {
    input {
      leaf in {
        type string;
      }
    }
  }
}
