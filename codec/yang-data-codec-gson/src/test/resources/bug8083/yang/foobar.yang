module foobar {

    namespace foobar-ns;
    prefix foobar-prefix;

    container top-cont {
        list keyed-list {
            key iid-key-leaf;

            leaf iid-key-leaf {
                type instance-identifier;
            }

            leaf regular-leaf {
                type int32;
            }
        }

        leaf iid-leaf {
            type instance-identifier;
        }

        leaf leaf-b {
            type int32;
        }
    }
}
