/*
 * Copyright (c) 2016 Intel Corporation and others.  All rights reserved.
 *
 * This program and the accompanying materials are made available under the
 * terms of the Eclipse Public License v1.0 which accompanies this distribution,
 * and is available at http://www.eclipse.org/legal/epl-v10.html
 */

module union-with-identityref {
    yang-version 1;
    namespace "union:identityref:test";
    prefix "unionidentityreftest";

    description "test union with identityref";

    revision "2016-07-12";

    identity ident-base;
    identity ident-one {
        base ident-base;
    }

    typedef union-type {
        type union {
            type uint8;
            type identityref {
                base ident-base;
            }
        }
    }

    container root {
        leaf leaf-value {
            type union-type;
        }
    }
}
