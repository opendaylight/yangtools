module foo {
  namespace foons;
  prefix foo;

  identity one;

  typedef bitz {
    type bits {
      bit one;
      bit two;
      bit three;
    }
  }

  list foo {
    key str;
    leaf str {
      type string;
    }
  }

  list bar {
    key qname;
    leaf qname {
      type identityref {
        base one;
      }
    }
  }

  list baz {
    key id;
    leaf id {
      type instance-identifier;
    }
  }

  list bee {
    key bts;
    leaf bts {
      type bitz;
    }
  }
}
