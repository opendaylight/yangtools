/*
 * Copyright (c) 2014 Cisco Systems, Inc. and others.  All rights reserved.
 *
 * This program and the accompanying materials are made available under the
 * terms of the Eclipse Public License v1.0 which accompanies this distribution,
 * and is available at http://www.eclipse.org/legal/epl-v10.html
 */
module leafref-test {
    yang-version 1;
    namespace "urn:opendaylight:yangtools:leafref:test";
    prefix "lt";

    revision 2014-11-04 {
        description "Test deserialization value of leafref type.";
    }

    identity test-identity-base {
    }

    identity test-identity {
      base lt:test-identity-base;
    }

    container interface {
        leaf simpleValue {
            type instance-identifier;
        }
    }

    container cont2 {
        container cont3 {
            leaf leafname3 {
                type leafref {
                    path "../../pointToStringLeaf";
                }
            }
        }
        leaf pointToStringLeaf {
            type leafref {
                path "../stringleaf";
            }
        }

        leaf point-to-identityrefleaf {
            type leafref {
                path "../identityrefleaf";
            }
        }

        leaf identityrefleaf {
            type identityref {
              base lt:test-identity-base;
            }
        }

        leaf stringleaf {
            type string;
        }
        leaf absname {
            type leafref {
                path "/lt:interface/lt:simpleValue";
            }
        }
        leaf relname {
            type leafref {
                path "../../lt:interface/lt:simpleValue";
            }
        }
    }
}
