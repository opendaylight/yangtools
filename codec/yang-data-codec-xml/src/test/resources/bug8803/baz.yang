module baz {
    namespace baz-ns;
    prefix baz;

    container top-cont {
        list keyed-list {
            key key-leaf;

            leaf key-leaf {
                type int32;
            }
        }
    }
}
