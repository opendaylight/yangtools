module zab {

    namespace zab-ns;
    prefix zab-prefix;

    identity base-id;

    identity derived-id {
        base base-id;
    }

    container top-cont {
        list keyed-list {
            key identityref-key-leaf;

            leaf identityref-key-leaf {
                type identityref {
                    base base-id;
                }
            }

            leaf regular-leaf {
                type int32;
            }
        }

        leaf iid-leaf {
            type instance-identifier;
        }
    }
}
