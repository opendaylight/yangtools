module yt1899-rev {
  namespace yt1899-rev;
  prefix rev;

  revision 2019-01-01;

  container old {
    leaf old-leaf {
      type string;
    }
  }

  container renamed {
    leaf renamed-leaf {
      type string;
    }
  }
}
