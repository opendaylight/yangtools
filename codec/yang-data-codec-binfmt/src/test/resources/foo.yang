module foo {
  namespace foo;
  prefix foo;

  container foo {
    leaf bar {
      type string;
    }
  }

  container bar { 
    presence "is explicit";

    leaf baz {
      type string;
    }
  }
}
